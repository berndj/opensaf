SAF-LCK-MIB DEFINITIONS ::= BEGIN

IMPORTS
        DateAndTime, RowPointer,RowStatus,
        TruthValue, TEXTUAL-CONVENTION
                FROM SNMPv2-TC
        OBJECT-GROUP, NOTIFICATION-GROUP,
        MODULE-COMPLIANCE
                FROM SNMPv2-CONF
        MODULE-IDENTITY, OBJECT-TYPE,
        NOTIFICATION-TYPE, Counter64,
        Integer32, Unsigned32, Counter32
                FROM SNMPv2-SMI
        SnmpAdminString
                FROM SNMP-FRAMEWORK-MIB
        SafTimeStamp,  aisE
                FROM SAF-TC-MIB
        SafAISErrorReturnCode
                FROM SAF-AIS-TC-MIB;

safLck MODULE-IDENTITY
        LAST-UPDATED "200507191200Z" -- 19th July' 2005
        ORGANIZATION "Service Availability Forum Systems Management WG"
        CONTACT-INFO
                "
         Service Availability Forum 
	 Systems Management Working Group

	 5440 SW Westgate Drive, Suite 217
	 Portland, OR 97221
	 Phone: (503) 291-2576
	 Fax: (503) 297-1090

         e-mail: snmp@saforum.org

                 "
        DESCRIPTION
                "This MIB serves as the starting point to
                define the Lock Service MIB as
                as derived from the Service Availability Forum 
                Specification SAI-AIS-LCK-B.01.01 
                "
        REVISION "0402270000Z"
        DESCRIPTION "Prototype version 0.3."
          ::= { aisE 7  }

safLckObject       OBJECT IDENTIFIER  ::= { safLck 1 }
safLckScalarObject OBJECT IDENTIFIER  ::= { safLckObject 1 }
safLckTableObject  OBJECT IDENTIFIER  ::= { safLckObject 2 }
saLckNotifications OBJECT IDENTIFIER  ::= { safLckObject 3 }
saMIBCompliances   OBJECT IDENTIFIER  ::= { safLckObject 4 }

--***************************************************************************
--  Lock Service Specific Objects 
-- ***************************************************************************

safSpecVersion OBJECT-TYPE
        SYNTAX SnmpAdminString
        MAX-ACCESS read-only
        STATUS current
        DESCRIPTION " Version of the SAF specification this agent is
                      compliant to."
        REFERENCE   " SAF-SMWG-AIS-A-00.03 "
        ::= { safLckScalarObject 1 }

safAgentVendor OBJECT-TYPE
        SYNTAX SnmpAdminString
        MAX-ACCESS read-only
        STATUS current
        DESCRIPTION " Implementing vendor of this agent."
        REFERENCE   " SAF-SMWG-AIS-A-00.03 "
        ::= { safLckScalarObject  2 }


safAgentVendorProductRev OBJECT-TYPE
        SYNTAX Integer32
        MAX-ACCESS read-only
        STATUS current
        DESCRIPTION " Implementing vendors version number of this agent.
                      Set to 0 if undefined."
        REFERENCE   " SAF-SMWG-AIS-A-00.03 "
        ::= { safLckScalarObject 3 }

safServiceStartEnabled  OBJECT-TYPE
        SYNTAX TruthValue
        MAX-ACCESS read-only 
        STATUS current
        DESCRIPTION "This service is enabled to be started/stopped
                     via SNMP oprations."

        REFERENCE " SAF-SMWG-AIS-A-00.03  "
        ::= { safLckScalarObject  4 }

safServiceState  OBJECT-TYPE
        SYNTAX INTEGER { running(1),
                         stopped(2),
                         startingup(3),
                         shuttingdown(4),
                         unavailable(5)
        } 

        MAX-ACCESS read-write
        STATUS current
        DESCRIPTION  "safServiceState with an SNMP get() operation 
                      determines if a service is running, stopped,
                      transitioning state, or is unavailable.
        STATES :
        RUNNING - service is running. SNMP set() to RUNNING
                  would start a stopped service, provided
                  safServiceStartEnabled value is TRUE.

        STOPPED - service is stopped. SNMP set ()  to STOPPED would
                  stop a running service, provided
                  safServiceStartEnabled value is TRUE.

        STARTING_UP - Service is transitioning to starting state.
                      Set() operations on the service at this state
                      are ignored.

        SHUTTING_DOWN - Service is transitioning to stopped state.
                       Set() operations on the service at this state
                       are ignored.

        UNAVAILABLE - Service is unavailable at this time. No
                      set() operations are honored.
                     "
        
        REFERENCE " SAF-SMWG-AIS-A-00.03  "

        ::= { safLckScalarObject  5 }

-- ***************************************************************************
--  Tables for the Lock Service
-- ***************************************************************************

-- ***************************************************************************
--  Lock Resource Table
--
--   The Lock Resource Table contains information related to a Lock Resource,
--   which is a globally named cluster wide resource.
-- ***************************************************************************

saLckResourceTable OBJECT-TYPE
        SYNTAX SEQUENCE OF SaLckResourceEntry
        MAX-ACCESS not-accessible
        STATUS current
        DESCRIPTION
                "This table represents the current created Lock Resources in a SAF 
                 Cluster that haven't been closed yet."
        REFERENCE   " SAI-AIS-LCK-B.01.01 "
        ::= { safLckTableObject  1 }

saLckResourceEntry OBJECT-TYPE
        SYNTAX SaLckResourceEntry
        MAX-ACCESS not-accessible
        STATUS current
        DESCRIPTION 
                 "Lock Resource table entry."
        REFERENCE   " SAI-AIS-LCK-B.01.01 "
        INDEX { saLckResourceResourceName }
        ::= { saLckResourceTable 1 }

SaLckResourceEntry ::= SEQUENCE  {
                saLckResourceResourceName         SnmpAdminString,
         	saLckResourceCreationTimeStamp    SafTimeStamp,
                saLckResourceNumUsers             Unsigned32,
                saLckResourceIsOrphaned           TruthValue, 
                saLckResourceStrippedCount        Counter32
                }

saLckResourceResourceName  OBJECT-TYPE
        SYNTAX SnmpAdminString
        MAX-ACCESS accessible-for-notify
        STATUS current
        DESCRIPTION " Cluster wide name of this Lock Resource. "
        REFERENCE   " SAI-AIS-LCK-B.01.01 "
        ::= { saLckResourceEntry 1 }

saLckResourceCreationTimeStamp OBJECT-TYPE
        SYNTAX SafTimeStamp
        MAX-ACCESS read-only
        STATUS current
        DESCRIPTION
                "Absolute time in nano-seconds that depicts when the
				 the lock resource was created."
        REFERENCE " SAI-AIS-EVT-B.01.01 "
        ::= { saLckResourceEntry 2 }

saLckResourceNumUsers  OBJECT-TYPE
        SYNTAX Unsigned32
        MAX-ACCESS read-only
        STATUS current
        DESCRIPTION " The number of users of this lock resource as
        determined by an explicit saLckResourceOpen/Async() invocation."
        REFERENCE   " SAI-AIS-LCK-B.01.01 "
        ::= { saLckResourceEntry 3 }

saLckResourceIsOrphaned OBJECT-TYPE
        SYNTAX TruthValue
        MAX-ACCESS read-only
        STATUS current
        DESCRIPTION " This boolean indicates if there is a lock in the
                      grant queue of this resource that is an orphan.
                      This value will be always false if the optional
                      orphan lock feature isn't supported."
        REFERENCE   " SAI-AIS-LCK-B.01.01 "
        ::= { saLckResourceEntry 4 }

saLckResourceStrippedCount OBJECT-TYPE
        SYNTAX Counter32
        MAX-ACCESS read-only
        STATUS current
        DESCRIPTION " The number of times a lock has been stripped off a
        Lock Resouce. If lock orphaning is supported, this value will
        depict the number of times this Lock resource has been
        orphaned by a lock operation." 
        REFERENCE   " SAI-AIS-LCK-B.01.01 "
        ::= { saLckResourceEntry 5 }

-- *****************************************************************************
--   Notifications : This section enumerates the Traps that the LCK service is 
--   expected to support.
--   TrapObject  : Object values delivered in one or more traps which 
--                    are not defined in any previous scalar or table in
--                    this MIB.
--   Traps       : Actual Traps specified in this MIB
-- ******************************************************************************
-- saLckTrapObject  OBJECT IDENTIFIER ::= { saLckNotifications 1 }
-- saLckTraps       OBJECT IDENTIFIER ::= { saLckNotifications 2 }

-- saLckErrorCode OBJECT-TYPE
--         SYNTAX       SafAISErrorReturnCode
--         MAX-ACCESS   read-only
--         STATUS       current
--         DESCRIPTION
--            "A subset of Error code values that are possible
--             in the context of the Lck service. There is one trap case:
--             ServiceImpaired - The Lck service is impaired for some reason."
--         ::= { saLckTrapObject 1 }

-- ***************************************************************************
--   Traps 
-- ***************************************************************************
-- saLckAlarmServiceImpaired NOTIFICATION-TYPE
--         OBJECTS {
--                 saLckErrorCode
--                 }
--         STATUS             current
--         DESCRIPTION
--            "The LCK service is not able to provide its service for one
--             of several reasons. The 'saLckErrorCode' explains why LCK is
--             unable to provide service"
--         ::= { saLckTraps 1 }

-- saLckAlarmDeadlockDetected NOTIFICATION-TYPE
--         OBJECTS {
--                  saLckResourceResourceName
--                 }
--         STATUS             current
--         DESCRIPTION
--            "A potential deadlock was detected by the Lck service when 
--             a lock was sought on the resource indicated by the 
--             'saLckResourceResourceName'."

--         ::= { saLckTraps 2 }

-- ***************************************************************************
--    OBJECT GROUPS Declarations for SMIv2 
-- ***************************************************************************
-- saLckGroup OBJECT-GROUP
--          OBJECTS {
--                 safSpecVersion,
--                 safAgentVendor,
--                 safAgentVendorProductRev,
--                 safServiceStartEnabled,
--                 safServiceState,  
--                 saLckResourceResourceName,
-- 				saLckResourceCreationTimeStamp,
--                 saLckResourceNumUsers,
--                 saLckResourceIsOrphaned,
--                 saLckResourceStrippedCount,
--                 saLckErrorCode
--          }
--         STATUS current
--         DESCRIPTION "LOCK Compliance Group."
--         ::= { saMIBCompliances 1 }

-- saLckNotificationsGroup  NOTIFICATION-GROUP
--     NOTIFICATIONS { 
--                   saLckAlarmDeadlockDetected,
--                   saLckAlarmServiceImpaired
--      }
--     STATUS  current
--     DESCRIPTION
--             "The set of Notifications that must be supported by a Lck
--              implementation. Some of these notifications like saLckAlarmDeadlockDetected,
--              are only conditionally mandatory depending upon if the related features 
-- 			 are supported by the Lck service."
--     ::= { saMIBCompliances 2}

--- **************************************************************************
--- MODULE COMPLIANCE Declarations for SMIv2 
--- **************************************************************************

-- saLckMIBCompliance MODULE-COMPLIANCE
--    STATUS current
--    DESCRIPTION
--    "The compliance statement for SMIv2 compliance of 
--     SAF AIS Lock service MIB."
--    MODULE
--    MANDATORY-GROUPS {
--          saLckGroup,
--          saLckNotificationsGroup 
--    }
-- ::= { saMIBCompliances 3}

END
