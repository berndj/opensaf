SAF-EVT-MIB DEFINITIONS ::= BEGIN

IMPORTS
        DateAndTime,
        RowPointer,
        RowStatus,
        TruthValue,
        TEXTUAL-CONVENTION
                FROM SNMPv2-TC
        OBJECT-GROUP,
        NOTIFICATION-GROUP,
        MODULE-COMPLIANCE
                FROM SNMPv2-CONF
        MODULE-IDENTITY,
        OBJECT-TYPE,
        NOTIFICATION-TYPE,
        Counter64,
        Integer32,
        Unsigned32,
        Counter32
                FROM SNMPv2-SMI
        SnmpAdminString
                FROM SNMP-FRAMEWORK-MIB
        SafTimeStamp, 
        aisE
                FROM SAF-TC-MIB
        SafAISErrorReturnCode, SafUnsigned64
                FROM SAF-AIS-TC-MIB;

safEvt  MODULE-IDENTITY
        LAST-UPDATED "200507191200Z" -- 19th July' 2005
        ORGANIZATION "Service Availability Forum Systems Management WG"
        CONTACT-INFO
                "Sayandeb Saha, Stephen Mills
                 Motorola Inc.
                 120 Turnpike Rd.
                 Southborough, MA, 01772.
                 sayandeb.saha@motorola.com
                 stephen.mills@motorola.com
                "
        DESCRIPTION
         "This MIB serves as the starting point to
          define the Event Service MIB as
          as derived from the Service Availability Forum 
          Specification SAI-AIS-EVT-B.01.01. "
        REVISION "0402170000Z"
        DESCRIPTION "Prototype version 0.3."
          ::= { aisE 5  }

safEvtObject        OBJECT IDENTIFIER  ::= { safEvt 1 }
safEvtScalarObject  OBJECT IDENTIFIER  ::= { safEvtObject 1 }
safEvtTableObject   OBJECT IDENTIFIER  ::= { safEvtObject 2 }
saEvtNotifications  OBJECT IDENTIFIER  ::= { safEvtObject 3 }
saMIBCompliances    OBJECT IDENTIFIER  ::= { safEvtObject 4 }

-- *************************************************************************
--  Event Service Specific Objects 
-- *************************************************************************
safSpecVersion OBJECT-TYPE
        SYNTAX SnmpAdminString
        MAX-ACCESS read-only
        STATUS current
        DESCRIPTION " Version of the SAF specification this agent is
                      compliant to."
        REFERENCE " SAF-SMWG-AIS-A-00.03 "
        ::= { safEvtScalarObject 1 }

safAgentVendor OBJECT-TYPE
        SYNTAX SnmpAdminString
        MAX-ACCESS read-only
        STATUS current
        DESCRIPTION " Implementing vendor of this agent."
        REFERENCE " SAF-SMWG-AIS-A-00.03 "
        ::= { safEvtScalarObject 2 }


safAgentVendorProductRev OBJECT-TYPE
        SYNTAX Integer32
        MAX-ACCESS read-only
        STATUS current
        DESCRIPTION " Implementing vendors version number of this agent.
                      Set to 0 if undefined."
        REFERENCE " SAF-SMWG-AIS-A-00.03 "
        ::= { safEvtScalarObject 3 }

safServiceStartEnabled  OBJECT-TYPE
        SYNTAX TruthValue
        MAX-ACCESS read-only 
        STATUS current
        DESCRIPTION "This service is enabled to be started/stopped
                     via SNMP oprations."

        REFERENCE " SAF-SMWG-AIS-A-00.03  "
        ::= { safEvtScalarObject  4 }

safServiceState  OBJECT-TYPE
        SYNTAX INTEGER { running(1),
                         stopped(2),
                         startingup(3),
                         shuttingdown(4),
                         unavailable(5)
        } 

        MAX-ACCESS read-write
        STATUS current
        DESCRIPTION  "safServiceState with an SNMP get() operation 
                      determines if a service is running, stopped,
                      transitioning state, or is unavailable.
        STATES :
        RUNNING - service is running. SNMP set() to RUNNING
                  would start a stopped service, provided
                  safServiceStartEnabled value is TRUE.

        STOPPED - service is stopped. SNMP set ()  to STOPPED would
                  stop a running service, provided
                  safServiceStartEnabled value is TRUE.

        STARTING_UP - Service is transitioning to starting state.
                      Set() operations on the service at this state
                      are ignored.

        SUTTING_DOWN - Service is transitioning to stopped state.
                       Set() operations on the service at this state
                       are ignored.

        UNAVAILABLE - Service is unavailable at this time. No
                      set() operations are honored.
                     "
        
        REFERENCE " SAF-SMWG-AIS-A-00.03  "

        ::= { safEvtScalarObject  5 }

--- *************************************************************************
---  Event Channel Table
--
--   This table contains attributes associated with the channels maintained
--   by the Event Service.
--- *************************************************************************

saEvtChannelTable OBJECT-TYPE
        SYNTAX SEQUENCE OF SaEvtChannelEntry
        MAX-ACCESS not-accessible
        STATUS current
        DESCRIPTION
                "This table accounts for the currently created event channels
				 in the cluster which includes all event channels in the cluster
				 that haven't been unlinked."
        REFERENCE " SAI-AIS-EVT-B.01.01 "
        ::= { safEvtTableObject 1 }


saEvtChannelEntry OBJECT-TYPE
        SYNTAX SaEvtChannelEntry
        MAX-ACCESS not-accessible
        STATUS current
        DESCRIPTION
                "Channel representation for the SAF Event Service."
        REFERENCE " SAI-AIS-EVT-B.01.01 "
        INDEX { saEvtChannelName }
        ::= { saEvtChannelTable 1 }


SaEvtChannelEntry ::= SEQUENCE {
        saEvtChannelName                 SnmpAdminString,
        saEvtChannelCreationTimeStamp    SafTimeStamp,
        saEvtChannelNumUsers             Unsigned32,
        saEvtChannelNumSubscribers       Unsigned32,
        saEvtChannelNumPublishers        Unsigned32,
        saEvtChannelNumRetainedEvents    Unsigned32,
        saEvtChannelLostEventsEventCount Counter32
        }

saEvtChannelName OBJECT-TYPE
        SYNTAX SnmpAdminString
        MAX-ACCESS accessible-for-notify
        STATUS current
        DESCRIPTION
                "The name assigned to a particular channel which is clusterwide
                 unique."
        REFERENCE " SAI-AIS-EVT-B.01.01 "
        ::= { saEvtChannelEntry 1 }


saEvtChannelCreationTimeStamp OBJECT-TYPE
        SYNTAX SafTimeStamp
        MAX-ACCESS read-only
        STATUS current
        DESCRIPTION
                "Time in nano-seconds of channel creation."
        REFERENCE " SAI-AIS-EVT-B.01.01 "
        ::= { saEvtChannelEntry 2 }


saEvtChannelNumUsers OBJECT-TYPE
        SYNTAX Unsigned32
        MAX-ACCESS read-only
        STATUS current
        DESCRIPTION
                "The number of current clients that have this channel open."
        REFERENCE " SAI-AIS-EVT-B.01.01 "
        ::= { saEvtChannelEntry 3 }

saEvtChannelNumSubscribers OBJECT-TYPE
        SYNTAX Unsigned32
        MAX-ACCESS read-only
        STATUS current
        DESCRIPTION
                "Of all the Users, there are these many that are subscribers."
        REFERENCE " SAI-AIS-EVT-B.01.01 "
        ::= { saEvtChannelEntry 4 }

saEvtChannelNumPublishers OBJECT-TYPE
        SYNTAX Unsigned32
        MAX-ACCESS read-only
        STATUS current
        DESCRIPTION
                "Of all the Users, there are these many that are publishers."
        REFERENCE " SAI-AIS-EVT-B.01.01 "
        ::= { saEvtChannelEntry 5 }

saEvtChannelNumRetainedEvents OBJECT-TYPE
        SYNTAX Unsigned32
        MAX-ACCESS read-only
        STATUS current
        DESCRIPTION
                "The number of Events that are currently retained on this 
                event channel due to time in nano-seconds left against its 
                specified retention timer value."
        REFERENCE " SAI-AIS-EVT-B.01.01 "
        ::= { saEvtChannelEntry 6 }

saEvtChannelLostEventsEventCount OBJECT-TYPE
        SYNTAX Counter32
        MAX-ACCESS read-only
        STATUS current
        DESCRIPTION
                "The number of Lost Event events sent by the event service to 
                 to subscribers indicating that the subscriber has lost events
                 for various reasons especially due to to communication
				 failures between the subscriber and publisher as outlined 
				 in section 3.3.7 of the document referenced below."                
				  
        REFERENCE " SAI-AIS-EVT-B.01.01 "
        ::= { saEvtChannelEntry 7 }

-- *****************************************************************************
--  Notifications : This section enumerates the Traps that the EVT service 
--  is expected to support.
--  TrapObject  : Object values delivered in one or more traps which 
--                are not defined in any previous scalar or table in this MIB.
--  Traps       : Actual Traps specified in this MIB
-- ******************************************************************************

saEvtTrapObject   OBJECT IDENTIFIER ::= { saEvtNotifications 1 }
saEvtTraps        OBJECT IDENTIFIER ::= { saEvtNotifications 2 }

saEvtSvcUserName     OBJECT-TYPE
        SYNTAX       SnmpAdminString
        MAX-ACCESS   read-only
        STATUS       current
        DESCRIPTION
           "If the user of the EVT service is part of a component under 
            the control of the Availability Management Framework this field 
            must contain the name of that component which is a LDAP DN. Otherwise 
            it is an Octet string that identifies (possibly 'well-known' 
            user/system defined) the current user of the checkpoint to the 
            system administrator."
        ::= { saEvtTrapObject 1 }

saEvtErrorCode       OBJECT-TYPE
        SYNTAX       SafAISErrorReturnCode
        MAX-ACCESS   read-only
        STATUS       current
        DESCRIPTION
           "A subset of Error code values that are possible
            in the context of the EVT service. There is one trap case:
            ServiceImpaired - The EVT service is impaired for some reason."
        ::= { saEvtTrapObject 2 }

-- *************************************************************************
--   Traps 
-- ************************************************************************* 
saEvtAlarmServiceImpaired NOTIFICATION-TYPE
        OBJECTS {
                 saEvtErrorCode
                }
        STATUS             current
        DESCRIPTION
           "The EVT service is not able to provide its service for one
            of several reasons. The 'saEvtErrorCode' explains why EVT is
            unable to provide service."
        ::= { saEvtTraps 1 }

saEvtAlarmSubscriberOverloaded NOTIFICATION-TYPE
        OBJECTS {
                 saEvtSvcUserName
                }
        STATUS current
        DESCRIPTION
           "This represents the case when the subscriber designated by 
            the 'saEvtSvcUserName' does not consume events fast enough and 
            there is no room left to queue events on it."
	    ::= { saEvtTraps 2 }

saEvtAlarmEventChannelOverloaded NOTIFICATION-TYPE
        OBJECTS {
                 saEvtChannelName
                }
        STATUS current
        DESCRIPTION
           "A particular event channel designated by 'saEvtChannelName'
            has been flooded with events and is unable to keep up with 
            the event flow. It has reached critical usage levels in terms 
            of memory or other resources and probably has too many yet to 
            be delivered retained events."
	    ::= { saEvtTraps 3 }



--- *************************************************************************
--    OBJECT GROUPS Declarations for SMIv2 
--- *************************************************************************

saEvtEventGroup OBJECT-GROUP
        OBJECTS {
                safSpecVersion, 
                safAgentVendor,
                safAgentVendorProductRev,
                safServiceStartEnabled,
                safServiceState,
                saEvtChannelName,
                saEvtChannelCreationTimeStamp,
                saEvtChannelNumUsers,
                saEvtChannelNumSubscribers,
                saEvtChannelNumPublishers,
                saEvtChannelNumRetainedEvents,
                saEvtChannelLostEventsEventCount,
				saEvtSvcUserName,
                saEvtErrorCode

        }
        STATUS current
        DESCRIPTION 
            "Event Compliance Group."
        ::= { saMIBCompliances 1 }

saEvtNotificationsGroup  NOTIFICATION-GROUP
    NOTIFICATIONS { 
                     saEvtAlarmSubscriberOverloaded,
                     saEvtAlarmEventChannelOverloaded,
                     saEvtAlarmServiceImpaired
    }
    STATUS  current
    DESCRIPTION
            "The set Notification that an implementation of the 
             event service must support."
    ::= { saMIBCompliances 2 }

--- **************************************************************************
--- MODULE COMPLIANCE Declarations for SMIv2 
--- **************************************************************************

saEvtMIBCompliance MODULE-COMPLIANCE
   STATUS current
   DESCRIPTION
   "The compliance statement for SMIv2 compliance of 
    SAF AIS EVT service MIB."
   MODULE
   MANDATORY-GROUPS {
         saEvtEventGroup,
         saEvtNotificationsGroup 
   }
::= { saMIBCompliances 3}

END
