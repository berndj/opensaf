NCS-IFSV-BIND-MIB DEFINITIONS ::= BEGIN

     IMPORTS
         OBJECT-TYPE, MODULE-IDENTITY, NOTIFICATION-TYPE,
         Integer32, Counter32, Unsigned32
             FROM SNMPv2-SMI
         MODULE-COMPLIANCE, OBJECT-GROUP, NOTIFICATION-GROUP
             FROM SNMPv2-CONF
         TEXTUAL-CONVENTION, TruthValue, RowStatus
                FROM SNMPv2-TC
         IANAifType               FROM IANAifType-MIB
         InterfaceIndex, ifNumber, ifEntry FROM IF-MIB
         openSafModules, ifsv
             FROM OPENSAF-SMI;
         


     ncsIfsvBindMIB MODULE-IDENTITY
         LAST-UPDATED "200411281730Z"
         ORGANIZATION "OpenSAF Foundation"
         CONTACT-INFO
             "www.opensaf.org"
         DESCRIPTION
             "This MIB contains managed object definitions for the
              Interface Service for Netplane Core Services
              Services.

              (C) Copyright 2008 The OpenSAF Foundation

              This program is distributed in the hope that it will be useful, but
              WITHOUT ANY WARRANTY; without even the implied warranty of MERCHANTABILITY
              or FITNESS FOR A PARTICULAR PURPOSE. This file and program are licensed
              under the GNU Lesser General Public License Version 2.1, February 1999.
              The complete license can be accessed from the following location:
              http://opensource.org/licenses/lgpl-license.php
              See the Copying file included with the OpenSAF distribution for full
              licensing terms.

              Author(s): Emerson Network Power"

         ::= { openSafModules 4 }

     --****************************************************************

     -- standard not settled yet....
     -- ifsvMIB                OBJECT IDENTIFIER ::= { ncs 1 }

     --****************************************************************
     ncsifsvIfBindObjects          OBJECT IDENTIFIER ::= { ifsv 3 }

      

--  IFSV BINDING INTERFACE TABLE

     ncsIfsvBindIfTable OBJECT-TYPE
         SYNTAX      SEQUENCE OF NcsIfsvBindIfEntry
         MAX-ACCESS  not-accessible
         STATUS      current
         DESCRIPTION
             "This Table contains objects which is used 
              to create a binding interface. "
         ::= { ncsifsvIfBindObjects 1 }

     ncsIfsvBindIfEntry OBJECT-TYPE
         SYNTAX      NcsIfsvBindIfEntry
         MAX-ACCESS  not-accessible
         STATUS      current
         DESCRIPTION
             "An entry containing Binding interface management
              information."
         INDEX     { ncsIfsvBindIfBindPortNum }
         ::= { ncsIfsvBindIfTable 1 }

     NcsIfsvBindIfEntry ::= SEQUENCE {
         ncsIfsvBindIfBindPortNum           Integer32,
         ncsIfsvBindIfBindIfIndex           Integer32,
         ncsIfsvBindIfMasterIfIndex         Integer32,
         ncsIfsvBindIfSlaveIfIndex          Integer32,
         ncsIfsvBindIfBindRowStatus         RowStatus
     }

     ncsIfsvBindIfBindPortNum OBJECT-TYPE 
         SYNTAX      Integer32 (0..65535)
         MAX-ACCESS  not-accessible
         STATUS      current
         DESCRIPTION
             "The Binding port number is the index to this table.
              It is an incremental value from 0 given by the user.
              It should be  "
         ::= { ncsIfsvBindIfEntry 1 }

     ncsIfsvBindIfBindIfIndex OBJECT-TYPE
         SYNTAX      Integer32 (0..65535)
         MAX-ACCESS  read-only
         STATUS      current
         DESCRIPTION
             " "
         ::= { ncsIfsvBindIfEntry 2 }

     ncsIfsvBindIfMasterIfIndex OBJECT-TYPE 
         SYNTAX      Integer32 (0..65535)
         MAX-ACCESS  read-create
         STATUS      current
         DESCRIPTION
             " "
         ::= { ncsIfsvBindIfEntry 3 }

     ncsIfsvBindIfSlaveIfIndex OBJECT-TYPE 
         SYNTAX      Integer32 (0..65535)
         MAX-ACCESS  read-create
         STATUS      current
         DESCRIPTION
             " "
         ::= { ncsIfsvBindIfEntry 4 }

     ncsIfsvBindIfBindRowStatus OBJECT-TYPE 
         SYNTAX      RowStatus
         MAX-ACCESS  read-create
         STATUS      current
         DESCRIPTION
             " "
         ::= { ncsIfsvBindIfEntry 5 }
END
