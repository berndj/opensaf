ECC-SMI DEFINITIONS ::= BEGIN
    IMPORTS
    	enterprises, MODULE-IDENTITY
    FROM SNMPv2-SMI;

-- Contact Info
-- www.opensaf.org
 
-- REVISION HISTORY
-- 27th Jan 2005
-- Initial Version with numbers allotted for NCS services.

-- The root of the OID sub-tree assigned to Motorola by the IANA
motorola        OBJECT IDENTIFIER ::= { enterprises 161 }  

-- Root for Computer Group/ECCG
computerGroup   OBJECT IDENTIFIER ::= { motorola 10 } 

-- Subtree for common object and event definitions 
eccgGen       	OBJECT IDENTIFIER ::= { computerGroup 1 }

-- Sub-tree for specific object and event definitions
eccgProducts    OBJECT IDENTIFIER ::= { computerGroup 2 }

-- Sub-tree for experimental definitions
eccgExp    	OBJECT IDENTIFIER ::= { computerGroup 3 }

-- Sub-tree for registrations. These object identifiers may be 
-- returned as the values of SNMP queries
eccgReg    	OBJECT IDENTIFIER ::= { computerGroup 4 }

-- Sub-tree for agent profiles
eccgCaps 	OBJECT IDENTIFIER ::= { computerGroup 5 }

-- Subtree for experimental generic definitions
eccgGenExp      OBJECT IDENTIFIER ::= { eccgExp 1 }

-- Subtree for experimental, product specific objects and events
eccgProductsExp OBJECT IDENTIFIER ::= { eccgExp 2 }

-- Identities assigned to different modules created by Motorola ECC
eccgNcsModules OBJECT IDENTIFIER ::= { eccgReg 1 }
eccgAXP OBJECT IDENTIFIER ::= { eccgReg 2 }

-- NetPlane Core Services
ncs 	OBJECT IDENTIFIER ::= { eccgGen 1}

-- Availability Service
avsv 	OBJECT IDENTIFIER ::= { ncs  1 }

-- Interface Service
ifsv 	OBJECT IDENTIFIER ::= { ncs  2 }

-- Checkpoint Service
cpsv 	OBJECT IDENTIFIER ::= { ncs  3 }

-- Event Distribution Service
edsv 	OBJECT IDENTIFIER ::= { ncs  4 }

-- System Resource Monitoring
srmsv 	OBJECT IDENTIFIER ::= { ncs  5 }

-- Distributed Tracing Service
dtsv 	OBJECT IDENTIFIER ::= { ncs  6 }

-- Persistence Store and Restore service
pssv 	OBJECT IDENTIFIER ::= { ncs  7 }

-- Management Access Service
masv 	OBJECT IDENTIFIER ::= { ncs  8 }

-- NCS SNMP SubAgent
ncsSa 	OBJECT IDENTIFIER ::= { ncs  9 }

-- Availability Manager
avm 	OBJECT IDENTIFIER ::= { ncs  10 }

-- Generic for NCS 
generic OBJECT IDENTIFIER ::= { ncs  11 }

-- ncs Virtula Interface service
ncsVip 	OBJECT IDENTIFIER ::= { ncs  12 }

-- Netplane Fault Management service
nfm 	OBJECT IDENTIFIER ::= { ncs  13 }

-- Simple Software Upgrate Service
ssu  	OBJECT IDENTIFIER ::= { ncs  14 }
   
END
