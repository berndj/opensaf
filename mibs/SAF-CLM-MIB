SAF-CLUSTER-MIB DEFINITIONS ::= BEGIN

IMPORTS
        MODULE-IDENTITY, OBJECT-TYPE,
        NOTIFICATION-TYPE, Unsigned32,
        Counter32, Counter64, Integer32          
                    FROM SNMPv2-SMI
        TEXTUAL-CONVENTION, DateAndTime,
        RowPointer,
        RowStatus, TruthValue          
                    FROM SNMPv2-TC
        MODULE-COMPLIANCE, OBJECT-GROUP, 
        NOTIFICATION-GROUP
                    FROM SNMPv2-CONF
        SnmpAdminString
                    FROM SNMP-FRAMEWORK-MIB
        SafTimeStamp,
        aisE
                    FROM SAF-TC-MIB
        SafAISErrorReturnCode
                    FROM SAF-AIS-TC-MIB;

safcluster MODULE-IDENTITY

    LAST-UPDATED "200507191200Z" -- 19th July' 2005
    ORGANIZATION "Service Availability Forum Systems Management WG"
    CONTACT-INFO "
    Bill Swortwood
    Postal: Motorola Computer Group
    2900 S. Diablo Way
    Tempe, Az 85282
    USA
    E-mail: bill.swortwood@motorola.com
        "
    DESCRIPTION
    " This MIB defines the Cluster Member Service MIB as
     as derived from the Service Availability Forum
     Application Interface Specification SAI-AIS-CLM-B.01.00
    "
   REVISION "200409290110Z"
   DESCRIPTION " Prototype version 0.4. "

        ::= { aisE 3 }

safClmObject       OBJECT IDENTIFIER  ::= { safcluster   1 }
safClmScalarObject OBJECT IDENTIFIER  ::= { safClmObject 1 }
safClmTableObject  OBJECT IDENTIFIER  ::= { safClmObject 2 }
saClmNotifications OBJECT IDENTIFIER  ::= { safClmObject 3 }
saMIBCompliances   OBJECT IDENTIFIER  ::= { safClmObject 4 }

--- ***************************************************************************
--  Cluster Scalar objects
--- ***************************************************************************

saClmAgentSpecVersion OBJECT-TYPE
        SYNTAX SnmpAdminString
        MAX-ACCESS read-only
        STATUS current
        DESCRIPTION " Version of the SAF specification this agent is
                      compliant to."

        REFERENCE " SAF-SMWG-AIS-A-00.03  "

        ::= { safClmScalarObject 1 }


saClmAgentVendor OBJECT-TYPE
        SYNTAX SnmpAdminString
        MAX-ACCESS read-only
        STATUS current
        DESCRIPTION " Implementing vendor of this agent."
        REFERENCE " SAF-SMWG-AIS-A-00.03  "
        ::= { safClmScalarObject 2 }

saClmAgentVendorProductRev OBJECT-TYPE
        SYNTAX Integer32
        MAX-ACCESS read-only
        STATUS current
        DESCRIPTION " Implementing vendors version number of this agent.
                      Set to 0 if undefined."
        
        REFERENCE " SAF-SMWG-AIS-A-00.03  "
        
        ::= { safClmScalarObject 3 }

saClmServiceStartEnabled  OBJECT-TYPE
        SYNTAX TruthValue
        MAX-ACCESS read-only 
        STATUS current
        DESCRIPTION "This service is enabled to be started/stopped
                     via SNMP oprations."

        REFERENCE " SAF-SMWG-AIS-A-00.03  "
        ::= { safClmScalarObject 4 }

saClmServiceState  OBJECT-TYPE
        SYNTAX INTEGER { running(1),
                         stopped(2),
                         startingup(3),
                         shuttingdown(4),
                         unavailable(5)
        } 

        MAX-ACCESS read-write
        STATUS current
        DESCRIPTION  " 
                safServiceState with an SNMP get() operation 
                determines if a service is running, stopped,
                transitioning state, or is unavailable.

                STATES :

                RUNNING - service is running. SNMP set() to RUNNING
                        would start a stopped service, provided
                        safServiceStartEnabled value is TRUE.

                STOPPED - service is stopped. SNMP set ()  to STOPPED would
                          stop a running service, provided
                          safServiceStartEnabled value is TRUE.

                STARTING_UP - Service is transitioning to starting state.
                              Set() operations on the service at this state
                              are ignored.

                SHUTTING_DOWN - Service is transitioning to stopped state.
                              Set() operations on the service at this state
                              are ignored.

                UNAVAILABLE - Service is unavailable at this time. No
                              set() operations are honored.
                     "
        
        REFERENCE " SAF-SMWG-AIS-A-00.03  "

        ::= { safClmScalarObject  5 }


saClmNumNodes OBJECT-TYPE 
        SYNTAX          Unsigned32
        MAX-ACCESS      read-only
        STATUS          current
        DESCRIPTION     "The object identifies the number of nodes that
                         are currently members of the cluster."
        REFERENCE " SAI-AIS-CLM-B.01.00 "
        ::= {safClmScalarObject 6}


saClmClusterInitTime OBJECT-TYPE 
        SYNTAX          SafTimeStamp
        MAX-ACCESS      read-only
        STATUS          current
        DESCRIPTION     "The object identifies the timestamp
                         when the first node joined the cluster to
                         initialise the cluster."
        REFERENCE " SAI-AIS-CLM-B.01.00 "
        ::= {safClmScalarObject 7}
        
saClmNodesExitCount OBJECT-TYPE 
        SYNTAX          Counter32
        MAX-ACCESS      read-only
        STATUS          current
        DESCRIPTION     "The object identifies the number
                         of nodes that have exited the membership
                         since the cluster boot time. Corresponds to the
                         number of nodes whose 'isMember' attribute is false."
        REFERENCE " SAI-AIS-CLM-B.01.00 "
        ::= {safClmScalarObject 8}


--- ***************************************************************************
--  Cluster Node Members
--- ***************************************************************************

saClmNodeTable OBJECT-TYPE
        SYNTAX          SEQUENCE OF SaClmNodeTableEntry
        MAX-ACCESS      not-accessible
        STATUS          current
        DESCRIPTION     "
                        This table represents the Nodes managed by the
                        Cluster Membership Service."
        REFERENCE " SAI-AIS-CLM-B.01.00 "
        ::= {safClmTableObject 1 }


saClmNodeTableEntry OBJECT-TYPE
        SYNTAX          SaClmNodeTableEntry
        MAX-ACCESS      not-accessible
        STATUS          current
        DESCRIPTION     "
                        Node entry representation for the SAF Cluster
                        Membership Service.
                        "

        REFERENCE       " 
                        Service Availability Forum Application Interface
                        Specification 
                        SAI-AIS-CLM-B.01.00 Page 12.
                        " 
        INDEX   {  saClmNodeName }

        ::= {saClmNodeTable 1}

SaClmNodeTableEntry ::= SEQUENCE {
        saClmNodeName                      SnmpAdminString,
        saClmNodeID                        Unsigned32,
        saClmNodeAddressType               INTEGER,
        saClmNodeAddress                   OCTET STRING,
        saClmNodeIsMember                  TruthValue,
        saClmNodeBootTimeStamp             SafTimeStamp,
        saClmNodeInitialViewNumber         Counter64,
	saClmNodeHPIEntityPath             SnmpAdminString 
 } 


saClmNodeName      OBJECT-TYPE 
        SYNTAX          SnmpAdminString
        MAX-ACCESS      accessible-for-notify
        STATUS          current
        DESCRIPTION     "Node name that is unique in the cluster. Node names
                         are not attached to a particular piece of hardware
                         or a particular physical location of that hardware 
                         inside the cluster but rather to the ability (from
                         a provisioning and I/O connectivity point of view)
                         to host a particular set of components. This node name
                         must be identical to the name represented by saAmfNodeName
                         in the AMF MIB."
        REFERENCE " SAI-AIS-CLM-B.01.00 "
        ::= {saClmNodeTableEntry 1}


saClmNodeID OBJECT-TYPE 
        SYNTAX          Unsigned32
        MAX-ACCESS      read-only
        STATUS          current
        DESCRIPTION     "Node identifier that is unique in the cluster. 
                         A given nodeId identifies a node only for as long 
                         as the node is a member of the cluster membership"
        REFERENCE " SAI-AIS-CLM-B.01.00 "
        ::= {saClmNodeTableEntry 2}


saClmNodeAddressType   OBJECT-TYPE 
        SYNTAX  INTEGER { saclmafinet(1), 
                          saclmafinet6(2)}
        MAX-ACCESS      read-only
        STATUS          current
        DESCRIPTION     " 
                         Node network communication address type.
                         If this object is not configured then 
                         it will show the value as 0. " 
        REFERENCE " SAI-AIS-CLM-B.01.00 "
        ::= {saClmNodeTableEntry 3}
                   
saClmNodeAddress   OBJECT-TYPE 
        SYNTAX  OCTET STRING(SIZE(0..64))
        MAX-ACCESS      read-only
        STATUS          current
        DESCRIPTION     " 
                         Node network communication address
                        "
        REFERENCE " SAI-AIS-CLM-B.01.00 "
        ::= {saClmNodeTableEntry 4}
                        

saClmNodeIsMember       OBJECT-TYPE 
        SYNTAX          TruthValue
        MAX-ACCESS      read-only
        STATUS          current
        DESCRIPTION     " 
                         Is this Node a cluster member?
                        "
        REFERENCE " SAI-AIS-CLM-B.01.00 "
        ::= {saClmNodeTableEntry 5}

saClmNodeBootTimeStamp  OBJECT-TYPE 
        SYNTAX          SafTimeStamp
        MAX-ACCESS      read-only
        STATUS          current
        DESCRIPTION     " 
                        This value denotes the Timestamp
                        at which the node was last booted.
                        The value is in units of
                        nano seconds.
                        "
        REFERENCE " SAI-AIS-CLM-B.01.00 "
        ::= {saClmNodeTableEntry 6}

saClmNodeInitialViewNumber  OBJECT-TYPE
        SYNTAX              Counter64
        MAX-ACCESS          read-only
        STATUS              current
        DESCRIPTION     " 
                        initialViewNumber - The initial view number, i.e. the
                        view number when this node joined the cluster. It is OK
                        for two nodes joining at the same time to have the
                        same initial view numbers. The only requirement is that
                        if node N1 joins the cluster before node N2,
                        then initialViewNumber of N1 < initialViewNumber of N2.
                        "
        REFERENCE " SAI-AIS-CLM-B.01.00 "
        ::= {saClmNodeTableEntry 7}

saClmNodeHPIEntityPath      OBJECT-TYPE 
        SYNTAX              SnmpAdminString
        MAX-ACCESS          read-only
        STATUS              current
        DESCRIPTION     "The entity path of the HPI entity that 
		                 implements the CLM node."
        REFERENCE " SAI-AIS-CLM-B.01.00 "
        ::= {saClmNodeTableEntry 8}

-- *****************************************************************************
--  Notifications : This section enumerates the Traps that the CLM service is expected
--  to support.
--  TrapObject  : Object values delivered in one or more traps which 
--                are not defined in any previous scalar or table in
--                this MIB.
--  Traps       : Actual Traps specified in this MIB
-- ******************************************************************************
saClmTrapObject  OBJECT IDENTIFIER ::= { saClmNotifications 1 }
saClmTraps       OBJECT IDENTIFIER ::= { saClmNotifications 2 }

saClmErrorCode OBJECT-TYPE
        SYNTAX       SafAISErrorReturnCode
        MAX-ACCESS   read-only
        STATUS       current
        DESCRIPTION
           "A subset of Error code values that are possible
            in the context of the CLM service. There is one trap case:
            ServiceImpaired - The CLM service is impaired for some reason."
   ::= { saClmTrapObject 1 }

-- *************************************************************************
--   Traps 
-- *************************************************************************
saClmAlarmServiceImpaired NOTIFICATION-TYPE
        OBJECTS {
                 saClmErrorCode
           }
        STATUS             current
        DESCRIPTION
           "The CLM service is currently un-availabile to its clients because 
            of the reason designated by 'saClmErrorCode'"
	     ::= { saClmTraps 1 }

saClmStateChgClusterNodeEntry NOTIFICATION-TYPE
        OBJECTS {
                 saClmNodeName
           }
        STATUS             current
        DESCRIPTION
           "A new node designated by the Name, Id & Address joined the 
            cluster. "
        ::= { saClmTraps 2 }

saClmStateChgClusterNodeExit NOTIFICATION-TYPE
        OBJECTS {
                 saClmNodeName
           }
        STATUS             current
        DESCRIPTION
           "Node designated by the Name, Id & address has now exited the 
            cluster."
	     ::= { saClmTraps 3 }

saClmStateChgClusterNodeReconfigured NOTIFICATION-TYPE
        OBJECTS {
                 saClmNodeName
           }
        STATUS             current
        DESCRIPTION
           "One or more attributes of the Node designated by the Name, Id and address 
            in the Notification changed."
        ::= { saClmTraps 4 }


--- **************************************************************************
--    OBJECT GROUPS Declarations for SMIv2 
--- **************************************************************************
saClusterNodeGroup OBJECT-GROUP
        OBJECTS {
                saClmNodeName,
                saClmNodeID,
                saClmNodeAddressType,                
                saClmNodeAddress,
                saClmNodeIsMember,
                saClmNodeBootTimeStamp,
                saClmNodeInitialViewNumber,
				saClmNodeHPIEntityPath,
                saClmErrorCode
        }
        STATUS current
        DESCRIPTION
                "Node group"
        ::=  { saMIBCompliances 1}

saClusterManagerGroup OBJECT-GROUP
        OBJECTS {
                saClmAgentSpecVersion,
                saClmAgentVendor,
                saClmAgentVendorProductRev,
                saClmServiceStartEnabled,
                saClmServiceState,
                saClmClusterInitTime,
                saClmNumNodes,
                saClmNodesExitCount
        }
        STATUS current
        DESCRIPTION
                "Manager group"
        ::=  { saMIBCompliances 2}

saClusterNotificationsGroup  NOTIFICATION-GROUP
    NOTIFICATIONS { 
				   saClmAlarmServiceImpaired,
				   saClmStateChgClusterNodeEntry,
                   saClmStateChgClusterNodeExit,
                   saClmStateChgClusterNodeReconfigured
                  }
    STATUS  current
    DESCRIPTION
            "The notifications which indicate specific changes in the
             the Clm service."
    ::= { saMIBCompliances 3}


--- **************************************************************************
--  MODULE COMPLIANCE Declarations for SMIv2 
--- **************************************************************************

saClusterMIBCompliance MODULE-COMPLIANCE
        STATUS current
        DESCRIPTION
        "The compliance statement for SMIv2 compliance of Cluster
         Membership MIB."
        MODULE
        MANDATORY-GROUPS {
                saClusterNodeGroup,
                saClusterManagerGroup,
                saClusterNotificationsGroup 
        }
        ::=  { saMIBCompliances 4}


END
