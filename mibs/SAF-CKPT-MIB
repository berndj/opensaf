SAF-CKPT-MIB DEFINITIONS ::= BEGIN

IMPORTS
        DateAndTime, RowPointer,RowStatus,
        TruthValue, TEXTUAL-CONVENTION
                FROM SNMPv2-TC
        OBJECT-GROUP, NOTIFICATION-GROUP,
        MODULE-COMPLIANCE
                FROM SNMPv2-CONF
        MODULE-IDENTITY, OBJECT-TYPE,
        NOTIFICATION-TYPE, Counter64,
        Integer32, Unsigned32
                FROM SNMPv2-SMI
        SnmpAdminString
                FROM SNMP-FRAMEWORK-MIB
        SafAISErrorReturnCode
                    FROM SAF-AIS-TC-MIB 
        SafTimeStamp,  aisE
                FROM SAF-TC-MIB;

safCkpt  MODULE-IDENTITY
         LAST-UPDATED "200507191200Z" -- 19th July' 2005
         ORGANIZATION "Service Availability Forum Systems Management WG"
         CONTACT-INFO
                "Sayandeb Saha
                 Postal: Mototorola ECCG
                 120 Turnpike Rd.
                 Southborough, MA 01772
                 USA
                 E-mail: sayandeb.saha@motorola.com
                "
        DESCRIPTION
                "This MIB serves as the starting point to
                define the Checkpoint Service MIB as
                as derived from the Service Availability Forum 
                Specification SAI-AIS-CKPT-B.01.01 "
        REVISION "200402270000Z"
        DESCRIPTION
                "Initial version 0.1."
          ::= { aisE 4  }

safCkptObject       OBJECT IDENTIFIER  ::= { safCkpt 1 }
safCkptScalarObject OBJECT IDENTIFIER  ::= { safCkptObject 1 }
safCkptTableObject  OBJECT IDENTIFIER  ::= { safCkptObject 2 }
saCkptNotifications OBJECT IDENTIFIER  ::= { safCkptObject 3 }
saMIBCompliances    OBJECT IDENTIFIER  ::= { safCkptObject 4 }

-- *************************************************************************
--  Checkpoint Service Specific Objects 
-- *************************************************************************
safSpecVersion OBJECT-TYPE
        SYNTAX SnmpAdminString
        MAX-ACCESS read-only
        STATUS current
        DESCRIPTION " Version of the SAF specification this agent is
                      compliant to."
        REFERENCE   " SAF-SMWG-AIS-A-00.03 "
        ::= { safCkptScalarObject 1 }

safAgentVendor OBJECT-TYPE
        SYNTAX SnmpAdminString
        MAX-ACCESS read-only
        STATUS current
        DESCRIPTION " Implementing vendor of this agent."
        REFERENCE   " SAF-SMWG-AIS-A-00.03 "
        ::= { safCkptScalarObject  2 }


safAgentVendorProductRev OBJECT-TYPE
        SYNTAX Integer32
        MAX-ACCESS read-only
        STATUS current
        DESCRIPTION " Implementing vendors version number of this agent.
                      Set to 0 if undefined."
        REFERENCE   " SAF-SMWG-AIS-A-00.03 "
        ::= { safCkptScalarObject 3 }

safServiceStartEnabled  OBJECT-TYPE
        SYNTAX TruthValue
        MAX-ACCESS read-only 
        STATUS current
        DESCRIPTION "This service is enabled to be started/stopped
                     via SNMP oprations."

        REFERENCE " SAF-SMWG-AIS-A-00.03  "
        ::= { safCkptScalarObject  4 }

safServiceState  OBJECT-TYPE
        SYNTAX INTEGER { running(1),
                         stopped(2),
                         startingup(3),
                         shuttingdown(4),
                         unavailable(5)
        } 

        MAX-ACCESS read-write
        STATUS current
        DESCRIPTION  "safServiceState with an SNMP get() operation 
                      determines if a service is running, stopped,
                      transitioning state, or is unavailable.
        STATES :
        RUNNING - service is running. SNMP set() to RUNNING
                  would start a stopped service, provided
                  safServiceStartEnabled value is TRUE.

        STOPPED - service is stopped. SNMP set ()  to STOPPED would
                  stop a running service, provided
                  safServiceStartEnabled value is TRUE.

        STARTING_UP - Service is transitioning to starting state.
                      Set() operations on the service at this state
                      are ignored.

        SHUTTING_DOWN - Service is transitioning to stopped state.
                       Set() operations on the service at this state
                       are ignored.

        UNAVAILABLE - Service is unavailable at this time. No
                      set() operations are honored.
                     "
        
        REFERENCE " SAF-SMWG-AIS-A-00.03  "

        ::= { safCkptScalarObject  5 }


-- *************************************************************************
--  Checkpoint Table Listing - primarily reflects creation attributes and
-- some dynamic attributes of a checkpoint.
-- *************************************************************************

saCkptCheckpointTable OBJECT-TYPE
        SYNTAX SEQUENCE OF SaCkptCheckpointEntry
        MAX-ACCESS not-accessible
        STATUS current
        DESCRIPTION
                "This table accounts for the currently created checkpoints
				 in the cluster which includes all checkpoints in the cluster
				 that haven't been unlinked."
        REFERENCE   " SAI-AIS-CKPT-B.01.01 "
        ::= { safCkptTableObject  1 }

saCkptCheckpointEntry OBJECT-TYPE
        SYNTAX SaCkptCheckpointEntry
        MAX-ACCESS not-accessible
        STATUS current
        DESCRIPTION
                "Checkpoint Representation table entry."
        REFERENCE   " SAI-AIS-CKPT-B.01.01 "
        INDEX { saCkptCheckpointName }
        ::= { saCkptCheckpointTable 1 }

SaCkptCheckpointEntry ::= SEQUENCE  {
                saCkptCheckpointName               SnmpAdminString,
                saCkptCheckpointSize               Counter64,
				saCkptCheckpointUsedSize           Counter64, 
                saCkptCheckpointCreateTime         SafTimeStamp,
                saCkptCheckpointUpdateOption       INTEGER,
                saCkptCheckpointIsCollocated       TruthValue,
                saCkptCheckpointRetDuration        SafTimeStamp,
                saCkptCheckpointMaxSections        Unsigned32,
                saCkptCheckpointMaxSectionSize     Counter64,
                saCkptCheckpointMaxSectionIdSize   Counter64,
                saCkptCheckpointNumOpeners         Unsigned32,
                saCkptCheckpointNumReaders         Unsigned32, 
                saCkptCheckpointNumWriters         Unsigned32,
                saCkptCheckpointNumReplica         Unsigned32,
                saCkptCheckpointNumSections        Unsigned32,
                saCkptCheckpointNumCorruptSections Unsigned32 
                }

saCkptCheckpointName  OBJECT-TYPE
        SYNTAX SnmpAdminString
        MAX-ACCESS accessible-for-notify
        STATUS current
        DESCRIPTION " Cluster wide LDAP name of this checkpoint "
        REFERENCE   " SAI-AIS-CKPT-B.01.01 "
        ::= { saCkptCheckpointEntry 1 }

saCkptCheckpointSize  OBJECT-TYPE
        SYNTAX Counter64
        MAX-ACCESS read-only
        STATUS current
        DESCRIPTION " The net size in bytes of each checkpoint replica 
                      that can be used for application data. "
        REFERENCE   " SAI-AIS-CKPT-B.01.01 "
        ::= { saCkptCheckpointEntry 2 }

saCkptCheckpointUsedSize  OBJECT-TYPE
        SYNTAX Counter64
        MAX-ACCESS read-only
        STATUS current
        DESCRIPTION " The current cumulative total number of the bytes used of the
                      available bytes for the checkpoint. This number is a sum-total
					  of all the data in bytes that occupies various sections of the 
					  checkpoint."
        REFERENCE   " SAI-AIS-CKPT-B.01.01 "
        ::= { saCkptCheckpointEntry 3 }

saCkptCheckpointCreateTime  OBJECT-TYPE
        SYNTAX SafTimeStamp
        MAX-ACCESS read-only
        STATUS current
        DESCRIPTION " Indicates the absolute time when this checkpoint
                      was created in nanoseconds. "
        REFERENCE   " SAI-AIS-CKPT-B.01.01 "
        ::= { saCkptCheckpointEntry 4 }

saCkptCheckpointUpdateOption  OBJECT-TYPE
        SYNTAX INTEGER { synchronous(1), 
                         asynchronous(2), 
                         asynchronousweak(3)
                  }
        MAX-ACCESS read-only
        STATUS current
        DESCRIPTION " Checkpoint update option chosen at creation time. "
        REFERENCE   " SAI-AIS-CKPT-B.01.01 "
        ::= { saCkptCheckpointEntry 5 }

saCkptCheckpointIsCollocated  OBJECT-TYPE
        SYNTAX TruthValue
        MAX-ACCESS read-only
        STATUS current
        DESCRIPTION " Is this checkpoint created with the collocated attribute?"
        REFERENCE   " SAI-AIS-CKPT-B.01.01 "
        ::= { saCkptCheckpointEntry 6 }

saCkptCheckpointRetDuration OBJECT-TYPE
        SYNTAX SafTimeStamp
        MAX-ACCESS read-only
        STATUS current
        DESCRIPTION " Retention Duration for this checkpoint in nanoseconds."
        REFERENCE   " SAI-AIS-CKPT-B.01.01 "
        ::= { saCkptCheckpointEntry 7 }

saCkptCheckpointMaxSections OBJECT-TYPE
        SYNTAX Unsigned32
        MAX-ACCESS read-only
        STATUS current
        DESCRIPTION " Maximum number of sections allowed for this checkpoint
                      configured at creation time."
        REFERENCE   " SAI-AIS-CKPT-B.01.01 "
        ::= { saCkptCheckpointEntry 8 }

saCkptCheckpointMaxSectionSize OBJECT-TYPE
        SYNTAX Counter64
        MAX-ACCESS read-only
        STATUS current
        DESCRIPTION " Maximum size of the section that can be housed
                      within this checkpoint configured at creation time."
        REFERENCE   " SAI-AIS-CKPT-B.01.01 "
        ::= { saCkptCheckpointEntry 9 }

saCkptCheckpointMaxSectionIdSize OBJECT-TYPE
        SYNTAX Counter64
        MAX-ACCESS read-only
        STATUS current
        DESCRIPTION " Maximum section ID size for this checkpoint configured
                      at creation time."
        REFERENCE   " SAI-AIS-CKPT-B.01.01 "
        ::= { saCkptCheckpointEntry 10 }

saCkptCheckpointNumOpeners OBJECT-TYPE  
        SYNTAX Unsigned32
        MAX-ACCESS read-only
        STATUS current
        DESCRIPTION "The number of times a checkpoint has been opened by
                     invocation of either the API saCkptCheckpointOpen() or
                     saCkptCheckpointOpenAsync() functions as described in the
					 document referenced below."
        REFERENCE   " SAI-AIS-CKPT-B.01.01 "
        ::= { saCkptCheckpointEntry 11 }

saCkptCheckpointNumReaders OBJECT-TYPE
        SYNTAX Unsigned32
        MAX-ACCESS read-only
        STATUS current
        DESCRIPTION " Number of times the checkpoint has been opened
		              by an invocation of the API saCkptCheckpointOpen() or
                      saCkptCheckpointOpenAsync() with SA_CKPT_CHECKPOINT_READ
					  flag. If a checkpoint is opened with both read and write 
					  access this counter is incremented once."
        REFERENCE   " SAI-AIS-CKPT-B.01.01 "
        ::= { saCkptCheckpointEntry 12 }

saCkptCheckpointNumWriters OBJECT-TYPE
        SYNTAX Unsigned32
        MAX-ACCESS read-only
        STATUS current
        DESCRIPTION " Number of times the checkpoint has been opened
		              by an invocation of the API saCkptCheckpointOpen() or
                      saCkptCheckpointOpenAsync() with SA_CKPT_CHECKPOINT_WRITE
					  flag. If a checkpoint is opened with both read and write 
					  access this counter is incremented once."
        REFERENCE   " SAI-AIS-CKPT-B.01.01 "
        ::= { saCkptCheckpointEntry 13 }

saCkptCheckpointNumReplica OBJECT-TYPE
        SYNTAX Unsigned32
        MAX-ACCESS read-only
        STATUS current
        DESCRIPTION " The current number of replicas for this checkpoint."
        REFERENCE   " SAI-AIS-CKPT-B.01.01 "
        ::= { saCkptCheckpointEntry 14 }

saCkptCheckpointNumSections OBJECT-TYPE
        SYNTAX Unsigned32
        MAX-ACCESS read-only
        STATUS current
        DESCRIPTION " The current number of sections housed
                      by this checkpoint."
        REFERENCE   " SAI-AIS-CKPT-B.01.01 "
        ::= { saCkptCheckpointEntry 15 }

saCkptCheckpointNumCorruptSections OBJECT-TYPE
        SYNTAX Unsigned32
        MAX-ACCESS read-only
        STATUS current
        DESCRIPTION " The current number of corrupt sections housed
                      by this checkpoint."
        REFERENCE   " SAI-AIS-CKPT-B.01.01 "
        ::= { saCkptCheckpointEntry 16 }

-- *************************************************************************
-- Checkpoint-Node replica location - This is a read-only table that illustrates, 
-- on which nodes a particular checkpoint has replicas.
-- *************************************************************************
saCkptNodeReplicaLocTable OBJECT-TYPE
        SYNTAX SEQUENCE OF SaCkptNodeReplicaLocEntry
        MAX-ACCESS not-accessible
        STATUS current
        DESCRIPTION
                "This table reprsents the configurable attributes
                 within a node w.r.t to checkpoint replica creation"
        ::= {  safCkptTableObject  2 }

saCkptNodeReplicaLocEntry OBJECT-TYPE
        SYNTAX SaCkptNodeReplicaLocEntry
        MAX-ACCESS not-accessible
        STATUS current
        DESCRIPTION "Node Replica Location representation for SAF CKPT service"
        REFERENCE " SAI-AIS-CKPT-B.01.01."
        INDEX { saCkptCheckpointNameLoc, saCkptNodeNameLoc }
        ::= { saCkptNodeReplicaLocTable 1 }

SaCkptNodeReplicaLocEntry ::= SEQUENCE {
                saCkptCheckpointNameLoc       SnmpAdminString,
                saCkptNodeNameLoc             SnmpAdminString,
                saCkptNodeReplicaType         INTEGER 
               }

saCkptCheckpointNameLoc OBJECT-TYPE
        SYNTAX SnmpAdminString
        MAX-ACCESS accessible-for-notify
        STATUS current
        DESCRIPTION " Cluster wide unique DN of the checkpoint whose
                      replica locations are being sought in this table."
        REFERENCE " SAI-AIS-CKPT-B.01.01."
        ::= { saCkptNodeReplicaLocEntry 1 }

saCkptNodeNameLoc OBJECT-TYPE
        SYNTAX SnmpAdminString
        MAX-ACCESS accessible-for-notify
        STATUS current
        DESCRIPTION " Cluster wide unique Name of the node which
                      house at-least one replica of the checkpoint
                      designated by saCkptCheckpointNameLoc."
        REFERENCE " SAI-AIS-CKPT-B.01.01."
        ::= { saCkptNodeReplicaLocEntry 2 }

saCkptNodeReplicaType OBJECT-TYPE
        SYNTAX  INTEGER { active(1), 
                          notactive(2), 
                          noncollocated(3), 
                          createdwithsynchupdateoption(4) }
        MAX-ACCESS read-only
        STATUS current
        DESCRIPTION " Indicates if the node contains an active replica
                      of the checkpoint designated by 'saCkptCheckpointNameLoc'.
                      Applicable only for collocated checkpoints created with 
                      either asynchronous or asynchronousweak update option. The concept
                      of an active replica doesn't apply if the checkpoint is 
                      either non-collocated or collocated but created with a synchronous
                      update option and hence the other INTEGER values have been provided
                      to bring out those specific traits."
        REFERENCE " SAI-AIS-CKPT-B.01.01."
        ::= { saCkptNodeReplicaLocEntry 3 }

-- *****************************************************************************
--   Notifications : This section enumerates the Traps that the CKPT service is expected
--   to support.
--   TrapObject  : Object values delivered in one or more traps which 
--                    are not defined in any previous scalar or table in
--                    this MIB.
--   Traps       : Actual Traps specified in this MIB
-- ******************************************************************************
saCkptTrapObject  OBJECT IDENTIFIER ::= { saCkptNotifications 1 }
saCkptTraps       OBJECT IDENTIFIER ::= { saCkptNotifications 2 }

saCkptErrorCode OBJECT-TYPE
        SYNTAX       SafAISErrorReturnCode
        MAX-ACCESS   read-only
        STATUS       current
        DESCRIPTION
           "A subset of Error code values that are possible
            in the context of the CKPT service. There is one trap case:
            ServiceImpaired - The CKPT service is impaired for some reason."
        ::= { saCkptTrapObject 1 }

-- *************************************************************************
--   Traps 
-- ************************************************************************* 
saCkptAlarmServiceImpaired NOTIFICATION-TYPE
        OBJECTS {
                saCkptErrorCode
                }
        STATUS             current
        DESCRIPTION
           "The CKPT service is not able to provide its service for one
            of several reasons. The 'saCkptErrorCode' explains why CKPT is
            unable to provide service"
        ::= { saCkptTraps 1 }
		 
saCkptStateChgNoMoreSections NOTIFICATION-TYPE
        OBJECTS {
                 saCkptCheckpointName
                }
        STATUS             current
        DESCRIPTION
           "All sections within the checkpoint are full and no more space
            is left in the checkpoint for write access."
	     ::= { saCkptTraps 2 }

saCkptStateChgSectionsAvailable NOTIFICATION-TYPE
        OBJECTS {
                 saCkptCheckpointName
                }
        STATUS             current
        DESCRIPTION
           "At least one section within the checkpoint is available, after
            having recovered from a preceding 'saCkptStateChgNoMoreSections' 
			condition."
        ::= { saCkptTraps 3 }


-- *************************************************************************
--    OBJECT GROUPS Declarations for SMIv2 
-- *************************************************************************

 saCheckpointGroup OBJECT-GROUP
         OBJECTS {
                safSpecVersion ,
                safAgentVendor ,
                safAgentVendorProductRev ,
                safServiceStartEnabled,
                safServiceState,
                saCkptCheckpointName,
                saCkptCheckpointSize,
                saCkptCheckpointCreateTime,
                saCkptCheckpointUpdateOption  ,
                saCkptCheckpointIsCollocated  ,
                saCkptCheckpointRetDuration ,
                saCkptCheckpointMaxSections ,
                saCkptCheckpointMaxSectionSize ,
                saCkptCheckpointMaxSectionIdSize ,
                saCkptCheckpointNumOpeners ,
                saCkptCheckpointNumReaders ,
                saCkptCheckpointNumWriters ,
                saCkptCheckpointNumReplica ,
                saCkptCheckpointNumSections ,
                saCkptCheckpointNumCorruptSections,
                saCkptCheckpointNameLoc,
                saCkptNodeNameLoc,
                saCkptNodeReplicaType,
                saCkptErrorCode
                }
        STATUS current
        DESCRIPTION
                "Checkpoint Compliance Group."
      ::= { saMIBCompliances 1 }
      
 saCkptNotificationsGroup  NOTIFICATION-GROUP
    NOTIFICATIONS { 
                  saCkptAlarmServiceImpaired,
                  saCkptStateChgNoMoreSections,
                  saCkptStateChgSectionsAvailable
                  }
    STATUS  current
    DESCRIPTION
            "The notifications which indicate specific changes in the
             the Checkpoint service."
      ::= { saMIBCompliances 2}

--- **************************************************************************
--  MODULE COMPLIANCE Declarations for SMIv2 
--- **************************************************************************

saCkptMIBCompliance MODULE-COMPLIANCE
   STATUS current
   DESCRIPTION
   "The compliance statement for SMIv2 compliance of 
    SAF AIS Checkpoint service MIB."
   MODULE
   MANDATORY-GROUPS {
         saCheckpointGroup, 
         saCkptNotificationsGroup
   }
	 ::=  { saMIBCompliances 3}

END
