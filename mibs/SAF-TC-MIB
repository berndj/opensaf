SAF-TC-MIB DEFINITIONS ::= BEGIN

IMPORTS
        TruthValue, 
        TEXTUAL-CONVENTION
                                  FROM SNMPv2-TC
        OBJECT-GROUP, 
        MODULE-COMPLIANCE,
        NOTIFICATION-GROUP
                                  FROM SNMPv2-CONF
        MODULE-IDENTITY,  
        OBJECT-TYPE,
        Integer32,  
        IpAddress,  
	Counter64,
        NOTIFICATION-TYPE
                                  FROM SNMPv2-SMI;

safTCMIB MODULE-IDENTITY
         LAST-UPDATED "200505190000Z"
         ORGANIZATION "Service Availability Forum "
         CONTACT-INFO  "

         Service Availability Forum 
	 Systems Management Working Group

	 5440 SW Westgate Drive, Suite 217
	 Portland, OR 97221
	 Phone: (503) 291-2576
	 Fax: (503) 297-1090

         e-mail: snmp@saforum.org
                "
             
          DESCRIPTION " 
         Definition of Textual Conventions for 
         Service Availability Forum (TM)
         specified SNMP MIBS Copyright(c) 2004 ,
         Service Availability Forum (TM)  
         All Rights reserved
         VERSION 1.2 May 19, 2005

         These textual conventions are subject to modification by
         the Service Availability Forum (TM) as related SAF
         specifications require.
                "
          ::= { 1 3 6 1 4 1 18568 1 10 }

-- **********************************************************
--  SAF ENTERPRISE NAMESPACE TAXONOMY
-- **********************************************************
-- Decimal      Name                    Description          
-- **********************************************************
-- 0            reserved                reserved             
-- 1            experimental            experimental MIB
-- 2            draft                   SAF draft MIB
-- 3            published               SAF published MIB
-- **********************************************************
org             OBJECT IDENTIFIER ::= { iso 3 }
dod             OBJECT IDENTIFIER ::= { org 6 }
internet        OBJECT IDENTIFIER ::= { dod 1 }
private         OBJECT IDENTIFIER ::= { internet 4 }
enterprises     OBJECT IDENTIFIER ::= { private 1 }
saforum         OBJECT IDENTIFIER ::= { enterprises 18568 }

experimental    OBJECT IDENTIFIER ::= { saforum 1 }
draft           OBJECT IDENTIFIER ::= { saforum 2 }
published       OBJECT IDENTIFIER ::= { saforum 3 }
-- *********************************************************
-- SubGroup Assignments : Experimental
-- *********************************************************
hpiE            OBJECT IDENTIFIER ::= { experimental 1 }
aisE            OBJECT IDENTIFIER ::= { experimental 2 }
applicationE    OBJECT IDENTIFIER ::= { experimental 3 }
-- *********************************************************
-- SubGroup Assignments : Draft
-- *********************************************************
hpiD            OBJECT IDENTIFIER ::= { draft 1 }
aisD            OBJECT IDENTIFIER ::= { draft 2 }
applicationD    OBJECT IDENTIFIER ::= { draft 3 }
-- *********************************************************
-- SubGroup Assignments : Published
-- *********************************************************
hpi             OBJECT IDENTIFIER ::= { published 1 }
ais             OBJECT IDENTIFIER ::= { published 2 }
application     OBJECT IDENTIFIER ::= { published 3 }

-- *********************************************************
-- SAF DEFINED Application Experimental Assignments
-- *********************************************************
openhpi         OBJECT IDENTIFIER ::= { hpiE 1 } 


-- *********************************************************
-- SAF DEFINED TEXTUAL CONVENTIONS
-- *********************************************************

SafTimeStamp ::= TEXTUAL-CONVENTION
        STATUS       current
        DESCRIPTION
        "
 A time value represents the local time as the number of
 nanoseconds from 00:00:00, January 1, 1970, in a 64-bit
 signed integer. This format is sufficient to represent
 times with nano-second resolution from the year 1678 to
 2262. Every API which deals with time values must define
 the timezone used.

 It should be noted that although nano-second resolution
 is supported in the data type, the actual resolution
 provided by an implementation may be more limited than this.

 The value -2^63, which is 0x8000000000000000, is used
 to indicate 'unknown/unspecified time'.

         "
        SYNTAX  OCTET STRING (SIZE(8))


-- *********************************************************
--  END : SAF DEFINED TEXTUAL CONVENTIONS
-- *********************************************************
END
