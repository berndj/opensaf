--MIB for VIP Feature


NCS-VIP-MIB DEFINITIONS ::= BEGIN 
IMPORTS 
            MODULE-IDENTITY, OBJECT-TYPE, NOTIFICATION-TYPE,  mib-2,
            Counter32, Gauge32, Integer32, IpAddress, 
            Unsigned32, TimeTicks, Opaque, Counter64
                    FROM SNMPv2-SMI 

            TEXTUAL-CONVENTION, TruthValue, StorageType, RowStatus, 
            DisplayString, PhysAddress, MacAddress, TestAndIncr, 
            AutonomousType, VariablePointer, RowPointer, TimeStamp, 
            TimeInterval, DateAndTime, StorageType, TDomain, TAddress
                    FROM SNMPv2-TC 

            openSafModules, ncsVip
                    FROM OPENSAF-SMI
            
            MODULE-COMPLIANCE, OBJECT-GROUP, NOTIFICATION-GROUP
                    FROM SNMPv2-CONF;


ncsVIPMibModule MODULE-IDENTITY
	LAST-UPDATED "200508160000Z"
	ORGANIZATION "OpenSAF Foundation"
	CONTACT-INFO
		"www.opensaf.org"

	DESCRIPTION
  	     "This MIB has objects which help Configuring and show 
	      statistics of Virtual-IP feature.

              (C) Copyright 2008 The OpenSAF Foundation

              This program is distributed in the hope that it will be useful, but
              WITHOUT ANY WARRANTY; without even the implied warranty of MERCHANTABILITY
              or FITNESS FOR A PARTICULAR PURPOSE. This file and program are licensed
              under the GNU Lesser General Public License Version 2.1, February 1999.
              The complete license can be accessed from the following location:
              http://opensource.org/licenses/lgpl-license.php
              See the Copying file included with the OpenSAF distribution for full
              licensing terms.

              Author(s): Emerson Network Power"

	::= {openSafModules 12}


ncsVIPMibObjects   	OBJECT IDENTIFIER  ::= {ncsVip 1}
ncsVIPTables	    	OBJECT IDENTIFIER  ::= {ncsVIPMibObjects 1}

--
-- VIP CONFIGURATION TABLE
--
--
--VIP ConfigurationTable: This Table intends to show the Current Configuration
--of VIP Feature
--This table contains a set of VIP(virtual ip) entries, and each VIP entry is
--associated with an Application with a unique Index, Single VIP or a Pool 
--(both continuous or discontinuous set)of VIP's can be configured as part 
--of VIP feature.
--

ncsVIPTable OBJECT-TYPE
   SYNTAX		SEQUENCE OF NcsVIPEntry
   MAX-ACCESS		not-accessible
   STATUS		current
   DESCRIPTION
       "Table containing objects for Configuring VIP Feature"
   ::= { ncsVIPTables 1 }

ncsVIPEntry OBJECT-TYPE
   SYNTAX		NcsVIPEntry
   MAX-ACCESS		not-accessible
   STATUS		current
   DESCRIPTION
       "This table has parameters necessary to Configure/Display  
	VIP Configurations"
   INDEX{	ncsVIPServiceName, 	
		ncsVIPHandle, 
		ncsVIPIPAddress,	
		ncsVIPIPMask,
		ncsVIPInterfaceName,
		ncsVIPIPType
	}
	::= { ncsVIPTable 1 }


NcsVIPEntry ::= SEQUENCE {
  ncsVIPServiceName		DisplayString,
  ncsVIPHandle			INTEGER,
  ncsVIPIPAddress		IpAddress,
  ncsVIPIPMask			INTEGER,
  ncsVIPInterfaceName		DisplayString,
  ncsVIPIPType			INTEGER,
  ncsVIPEntryType		INTEGER,
  ncsVIPInstalledInterfaceName	DisplayString,
  ncsVIPIPRange			INTEGER,
  ncsVIPOperStatus		INTEGER,
  ncsVIPRowStatus		RowStatus
}


ncsVIPServiceName	OBJECT-TYPE
   SYNTAX			DisplayString (SIZE (0..128))
   MAX-ACCESS			not-accessible
   STATUS			current
   DESCRIPTION
	"The ServiceName is a String which Uniquely Identifies itself with 
         the Application"
   ::= { ncsVIPEntry 1}

ncsVIPHandle	OBJECT-TYPE
   SYNTAX			INTEGER(0..2147483647)
   MAX-ACCESS			not-accessible
   STATUS			current
   DESCRIPTION
       "The Handle is a 32 bit Integer which is used as part of INDEX to 
        Uniquely Identify a VIP entry"
   ::= { ncsVIPEntry 2}

ncsVIPIPAddress 	OBJECT-TYPE
   SYNTAX			IpAddress
   MAX-ACCESS			not-accessible
   STATUS			current
   DESCRIPTION
	"This IP Address has two significances, 
		1. If ncsVIPEntryType is set to 1(FreePool) and 
                   ncsVIPConfigureTableIPRange is set to a positive 
                   non-zero value, then ncsVIPIPAddress would specify the
                   Starting IP Address of a Range of IP Addresses
		2. If ncsVIPEntryType is set to 0(Configured) then 
                   ncsVIPConfigureTableIPAddress specifies an IPAddress
                   associated with that ServiceName"
   ::= { ncsVIPEntry 3}

ncsVIPIPMask 	OBJECT-TYPE
   SYNTAX			INTEGER(0..31)
   MAX-ACCESS			not-accessible
   STATUS			current
   DESCRIPTION
		"The IP Address Mask, the bit mask is dnoted as an Integer"
   ::= { ncsVIPEntry 4}

ncsVIPInterfaceName	OBJECT-TYPE
   SYNTAX			DisplayString
   MAX-ACCESS			not-accessible
   STATUS			current
   DESCRIPTION
	"This specifies either a bonding or non-bonding interface"
   ::= { ncsVIPEntry 5}

ncsVIPIPType		OBJECT-TYPE
   SYNTAX			INTEGER{
						defaultIP(0),
						internalIP(1),
						externalIP(2)
					}
   MAX-ACCESS			not-accessible
   STATUS			current
  DESCRIPTION
	"This specifies whether the IPAddress is Internal or External,
         Default is 0, it means Appplication has to mention whether IP is
         Internal or External"
  DEFVAL { defaultIP }
   ::= { ncsVIPEntry 6}

ncsVIPEntryType	OBJECT-TYPE
   SYNTAX			INTEGER{
						configured(1),
						freepool(2)
					}
   MAX-ACCESS			read-create
   STATUS			current
  DESCRIPTION
	"This specifies whether vip Entry is already Configured, or is yet
         to be configured from a freePool of IPAddresses"
  DEFVAL	{ configured }
   ::= { ncsVIPEntry 7}

ncsVIPIPRange	OBJECT-TYPE
   SYNTAX			INTEGER
   MAX-ACCESS			read-create
   STATUS			current
   DESCRIPTION
	"This Entry is of significance if  ncsVIPEntryType is set to
         2(Free Pool) and in that case this Entry denotes the range
         of IPAddresses Configured as part of the FreePool, For example
         if ncsVIPConfigureTableConfiguredEntry 2(FreePool),
         ncsVIPConfigureTableIPAddress is 10.20.10.10 and 
         ncsVIPConfigureTableIPRange is 10, then this entry specifies a
         series of IPAddresses from 10.20.10.10 to 10.20.10.20"
 DEFVAL	{ 1 }
   ::= { ncsVIPEntry 8}

ncsVIPInstalledInterfaceName   OBJECT-TYPE
   SYNTAX                       DisplayString
   MAX-ACCESS                   read-create
   STATUS                       current
   DESCRIPTION
        "This Entry gives the information of the Interface on which an 
         IP is installed"
   ::= { ncsVIPEntry 9}


ncsVIPOperStatus	OBJECT-TYPE
   SYNTAX			INTEGER{
						vipEntryNotInUse(0),
						vipEntryInUse(1)
					}
   MAX-ACCESS			read-only
   STATUS			current
   DESCRIPTION
	"This specifies whether the vip entry is in use or not, When the 
         row is active this cannot be Set"
  DEFVAL	{ vipEntryNotInUse }
   ::= { ncsVIPEntry 10}

ncsVIPRowStatus	OBJECT-TYPE
   SYNTAX			RowStatus
   MAX-ACCESS			read-create
   STATUS			current
   DESCRIPTION
        "This specifies whether the vip entry is in use or not, When the row
         is active this cannot be Set"
   ::= { ncsVIPEntry 11}

END
