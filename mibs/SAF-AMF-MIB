SAF-AMF-MIB DEFINITIONS ::= BEGIN

     IMPORTS
         OBJECT-TYPE, MODULE-IDENTITY, NOTIFICATION-TYPE,
         Integer32, Counter32, Unsigned32, Counter64  
             FROM SNMPv2-SMI
         MODULE-COMPLIANCE, OBJECT-GROUP, 
         NOTIFICATION-GROUP
             FROM SNMPv2-CONF
         RowStatus, TimeInterval, TruthValue,
         TimeStamp, StorageType, DisplayString, 
         TEXTUAL-CONVENTION
             FROM SNMPv2-TC
         SnmpAdminString
                    FROM SNMP-FRAMEWORK-MIB
         SafAISErrorReturnCode
                    FROM SAF-AIS-TC-MIB
         SafTimeStamp, aisE
                    FROM SAF-TC-MIB;

     saAmfMIB MODULE-IDENTITY
         LAST-UPDATED "200507191200Z" -- 19th July' 2005
         ORGANIZATION "Service Availability Forum"
         CONTACT-INFO
             "Sayandeb Saha
              Postal: Mototorola ECC
              120 Turnpike Rd.
              Southborough, MA 01772
              USA
              E-mail: sayandeb.saha@motorola.com"

         DESCRIPTION
             "This MIB contains managed object definitions for the
              Application Management Framework AIS Service
              Version B.01, with minor adjustements for strict SMIv2
              compliance."
         ::= { aisE 2 }

     --****************************************************************

     saAmfObjects              OBJECT IDENTIFIER ::= { saAmfMIB 1 }
    
     saAmfScalars              OBJECT IDENTIFIER ::= { saAmfObjects 1 }
     saAmfTables               OBJECT IDENTIFIER ::= { saAmfObjects 2 }
     safAmfNotifications       OBJECT IDENTIFIER ::= { saAmfObjects 3 }
     saAmfCompliances          OBJECT IDENTIFIER ::= { saAmfObjects 4 }
     
     --****************************************************************
     -- AMF specified conventions
     --****************************************************************     
          
     SaAmfHAState  ::= TEXTUAL-CONVENTION 
         STATUS current
         DESCRIPTION " The different HA states defined by AMF."
         SYNTAX INTEGER { active(1),
                          standby(2),
                          quiesced(3),
                          quiescing(4) }
        
        
     SafAmfCompCapabilityModel ::= TEXTUAL-CONVENTION
         STATUS current        
         DESCRIPTION " The different component capability
                       defined by AMF. "
         SYNTAX INTEGER {  xactiveandystandby(1),
                           xactiveorystandby(2),
                           oneactiveorxstandby(3),
                           oneactiveoronestandby(4),
                           xactive(5),
                           oneactive(6),
                           nostate(7) }


     SafAmfRecommendedRecovery ::= TEXTUAL-CONVENTION
         STATUS current        
         DESCRIPTION " The component recovery procedures defined
                       by AMF."
         SYNTAX INTEGER {  none(1),
                           componentrestart(2),
                           componentfailover(3),
                           nodeswitchover(4),
                           nodefailover(5),
                           nodefailfast(6),
                           clusterreset(7) }


     --****************************************************************
     -- AMF Scalar Objects
     --****************************************************************

     saAmfAgentSpecVersion OBJECT-TYPE
         SYNTAX SnmpAdminString
         MAX-ACCESS read-only
         STATUS current
         DESCRIPTION " Version of the SAF specification this agent is
                       compliant to."

         REFERENCE " SAF-SMWG-AIS-A-00.03  "

         ::= { saAmfScalars 1 }


     saAmfAgentVendor OBJECT-TYPE
         SYNTAX SnmpAdminString
         MAX-ACCESS read-only
         STATUS current
         DESCRIPTION " Implementing vendor of this agent."
         REFERENCE " SAF-SMWG-AIS-A-00.03  "

         ::= { saAmfScalars 2 }

     saAmfAgentVendorProductRev OBJECT-TYPE
         SYNTAX Integer32
         MAX-ACCESS read-only
         STATUS current
         DESCRIPTION " Implementing vendors version number of this agent.
                       Set to 0 if undefined."
        
         REFERENCE " SAF-SMWG-AIS-A-00.03  "
        
         ::= { saAmfScalars 3 }

     saAmfServiceStartEnabled  OBJECT-TYPE
         SYNTAX TruthValue
         MAX-ACCESS read-only 
         STATUS current
         DESCRIPTION "This service is enabled to be started/stopped
                      via SNMP oprations."
         REFERENCE " SAF-SMWG-AIS-A-00.03  "
         ::= { saAmfScalars 4 }

     saAmfServiceState  OBJECT-TYPE
         SYNTAX INTEGER { running(1),
                          stopped(2),
                          startingup(3),
                          shuttingdown(4),
                          unavailable(5)
         } 

         MAX-ACCESS read-write
         STATUS current
         DESCRIPTION  " 
                 safServiceState with an SNMP get() operation 
                 determines if a service is running, stopped,
                 transitioning state, or is unavailable.
 
                 STATES :
 
                 RUNNING - service is running. SNMP set() to RUNNING
                         would start a stopped service, provided
                         safServiceStartEnabled value is TRUE.
 
                 STOPPED - service is stopped. SNMP set ()  to STOPPED would
                           stop a running service, provided
                           safServiceStartEnabled value is TRUE.
 
                 STARTING_UP - Service is transitioning to starting state.
                               Set() operations on the service at this state
                               are ignored.
 
                 SHUTTING_DOWN - Service is transitioning to stopped state.
                               Set() operations on the service at this state
                               are ignored.
 
                 UNAVAILABLE - Service is unavailable at this time. No
                               set() operations are honored.
                      
                 The support for this Object is optional.
                     "
         
         REFERENCE " SAF-SMWG-AIS-A-00.03  "
 
         ::= { saAmfScalars 5 }   

     --****************************************************************
	 -- Things NOT accounted for in this version of the MIB are:
	 -- 1. Instrumentation for the Admin operations esp. restart, adjust, swap etc. .
	 -- 2. Integration of Application Logical entity concept.
	 -- 3. Operational state of a Node.
	 -- 4. Traps related to the 'Application' as well as the 
	 --    Operational state of a node.
     --****************************************************************

     --****************************************************************
     -- AMF Specific scalar
     --****************************************************************

      saAmfClusterStartupTimeout OBJECT-TYPE
          SYNTAX      SafTimeStamp
          MAX-ACCESS  read-write 
          STATUS      current
          DESCRIPTION
              "Time in nano-seconds from cluster start
               for which the AMF waits before pre-instantiating 
               SUs and assigning SIs. A value of 0 means that the AMF
               should use a default value instead. The instant of time
               which is designated as the cluster startup time is 
               implementation dependent."
           ::= { saAmfScalars 6 }
 

     --****************************************************************
     -- AMF Node Table Objects
     --****************************************************************
          
     saAmfNodeTable OBJECT-TYPE
         SYNTAX      SEQUENCE OF SaAmfNodeTableEntry
         MAX-ACCESS  not-accessible
         STATUS      current
         DESCRIPTION
             "The Node Table identifies all the Nodes
              that are configured within a cluster and
              their configuration details"
              
         ::= { saAmfTables 1 }

     saAmfNodeTableEntry OBJECT-TYPE
         SYNTAX      SaAmfNodeTableEntry
         MAX-ACCESS  not-accessible
         STATUS      current
         DESCRIPTION
             "An entry in this table represents a
              node configuration in SAF cluster 
              environment."
         INDEX       {  saAmfNodeName  }   
         ::= { saAmfNodeTable 1 }

     SaAmfNodeTableEntry ::= SEQUENCE {
         saAmfNodeName                           SnmpAdminString,
         saAmfNodeSuFailoverProb                 SafTimeStamp,
         saAmfNodeSuFailoverMax                  Unsigned32,
         saAmfNodeAdminState                     INTEGER,
         saAmfNodeRowStatus                      RowStatus
     }

     saAmfNodeName OBJECT-TYPE 
         SYNTAX      SnmpAdminString
         MAX-ACCESS  accessible-for-notify
         STATUS      current
         DESCRIPTION
             "A name that uniquely identifies the
              node within the scope of the cluster
              for which the SAF amf configuration
              is specified. The node name represented by 
              saClmNodeName in the CLM MIB and saAmfNodeName 
              MUST be identical"                    
         ::= { saAmfNodeTableEntry 1 }

     saAmfNodeSuFailoverProb OBJECT-TYPE 
         SYNTAX      SafTimeStamp
         MAX-ACCESS  read-create
         STATUS      current
         DESCRIPTION
             "The value of the SU failover
              probation period. The value
              is in units of nano seconds.
              The minimum value is
              10 milli seconds(10000000)."
         ::= { saAmfNodeTableEntry 2 }

     
     saAmfNodeSuFailoverMax OBJECT-TYPE 
         SYNTAX      Unsigned32(1..4294967295)
         MAX-ACCESS  read-create
         STATUS      current
         DESCRIPTION
             "The maximum number of times SUs
              can failover within the probation time,
              without causing a node failover. "
         ::= { saAmfNodeTableEntry 3 }


     saAmfNodeAdminState OBJECT-TYPE 
         SYNTAX      INTEGER { locked(1), unlocked(2), shuttingdown(3) }
         MAX-ACCESS  read-create
         STATUS      current

         DESCRIPTION
             "The desired administrative status
              of the node. Enables locking, unlocking 
              or shutting down of all SUs on the node."
           DEFVAL      { unlocked }
         ::= { saAmfNodeTableEntry 4 }


     saAmfNodeRowStatus OBJECT-TYPE 
         SYNTAX      RowStatus
         MAX-ACCESS  read-create
         STATUS      current
         DESCRIPTION
             "This variable is used to create,
              modify, and/or delete a row in
              this table. saAmfNodeSuFailoverProb
              and saAmfNodeSuFailoverMax objects
              need to be set to valid values
              to make the status active. This
              can be set to delete or not in
              service only after all the
              dependent SUs and components are
              deleted"
         ::= { saAmfNodeTableEntry 5 }


     --****************************************************************
     -- AMF Service Group Table Objects
     --****************************************************************


          
     saAmfSGTable OBJECT-TYPE
         SYNTAX      SEQUENCE OF SaAmfSGTableEntry
         MAX-ACCESS  not-accessible
         STATUS      current
         DESCRIPTION
             "The Service Group (SG) Table identifies
              all SGs that are configured in the 
              cluster, each having a unique SG-name."
              
         ::= { saAmfTables 2 }

     saAmfSGTableEntry OBJECT-TYPE
         SYNTAX      SaAmfSGTableEntry
         MAX-ACCESS  not-accessible
         STATUS      current
         DESCRIPTION
             "An entry in this table represents a 
              SG in the AMF cluster."
         INDEX       {  saAmfSGName  }
         ::= { saAmfSGTable 1 }

     SaAmfSGTableEntry ::= SEQUENCE {
         saAmfSGName                             SnmpAdminString,
         saAmfSGRedModel                         INTEGER,   
         saAmfSGFailbackOption                   TruthValue,  
         saAmfSGNumPrefActiveSUs                 Unsigned32,
         saAmfSGNumPrefStandbySUs                Unsigned32,
         saAmfSGNumPrefInserviceSUs              Unsigned32,
         saAmfSGNumPrefAssignedSUs               Unsigned32,  
         saAmfSGMaxActiveSIsperSU                Unsigned32,
         saAmfSGMaxStandbySIsperSU               Unsigned32,
         saAmfSGAdminState                       INTEGER,
         saAmfSGCompRestartProb                  SafTimeStamp,
         saAmfSGCompRestartMax                   Unsigned32,
         saAmfSGSuRestartProb                    SafTimeStamp,
         saAmfSGSuRestartMax                     Unsigned32,
         saAmfSGNumCurrAssignedSU                Counter32,   
         saAmfSGNumCurrNonInstantiatedSpareSU    Counter32,  
         saAmfSGNumCurrSpareSU                   Counter32,
         saAmfSGRowStatus                        RowStatus
     }

     saAmfSGName OBJECT-TYPE 
         SYNTAX      SnmpAdminString
         MAX-ACCESS  accessible-for-notify
         STATUS      current
         DESCRIPTION
             "An octet string that uniquely identifies a
              Service Group within the scope of a cluster."
         ::= { saAmfSGTableEntry 1 }

     saAmfSGRedModel OBJECT-TYPE 
         SYNTAX      INTEGER {twoN(1),nPlusM(2),
                              nWay(3),nWayActive(4),
                              noRedundancy(5)}
         MAX-ACCESS  read-create
         STATUS      current
         DESCRIPTION
             "This value contains the SGs
              redundancy model. Could be
              either 2N, N+M, N-Way,
              N-Way Active and No Redundancy.
              Writable only when
              saAmfSGRowStatus is not active"
         ::= { saAmfSGTableEntry 2 }


     saAmfSGFailbackOption OBJECT-TYPE 
         SYNTAX      TruthValue
         MAX-ACCESS  read-create
         STATUS      current
         DESCRIPTION
             "If set to TRUE, AMF should fail back
              the SUs to the preferred configuration.
              Default value is false."
         ::= { saAmfSGTableEntry 3 }

     saAmfSGNumPrefActiveSUs OBJECT-TYPE 
         SYNTAX      Unsigned32(0..4294967295)
         MAX-ACCESS  read-create
         STATUS      current
         DESCRIPTION
             "This Parameter indicates the preferred number of active service units
              at any time. The Availability Management Framework should try to
              guarantee that this number of active service units exist for the 
              service group, if the number of in-service service units is large 
              enough. This is only applicable for nplusM redundancy model.
              Writable only when saAmfSGRowStatus is not active."
         ::= { saAmfSGTableEntry 4 }

     saAmfSGNumPrefStandbySUs OBJECT-TYPE 
         SYNTAX      Unsigned32(0..4294967295)
         MAX-ACCESS  read-create
         STATUS      current
         DESCRIPTION
             "This is only applicable for nplusM
              redundancy model. It represents the 
              preferred number of SUs that should have 
              standby role assigned in nPlusM redundancy 
              model. Writable only when saAmfSGRowStatus 
              is not active."
         ::= { saAmfSGTableEntry 5 }

     saAmfSGNumPrefInserviceSUs OBJECT-TYPE 
         SYNTAX      Unsigned32(0..4294967295)
         MAX-ACCESS  read-create
         STATUS      current
         DESCRIPTION
             "The Availability Management Framework should ensure that 
              this number of in-service service units are instantiated, 
              if possible. This parameter should be greater than or equal 
              to 2 in the case of 2N, greater than or equal to the 
              sum of saAmfSGNumPrefActiveSUs and saAmfSGNumPrefStandbySUs 
              in the case of N+M, greater than or equal to saAmfSGPrefAssignedSUs 
              in the case of N-way and N-way active redundancy models. The configuration
              of this object is optional and by default this value equals the number of 
              SUs in the SG."
         ::= { saAmfSGTableEntry 6 }

     saAmfSGNumPrefAssignedSUs OBJECT-TYPE 
         SYNTAX      Unsigned32(0..4294967295)
         MAX-ACCESS  read-create
         STATUS      current
         DESCRIPTION
             "This indicates the preferred number of assigned service units at any time. 
              The Availability Management Framework should try to guarantee
              that this number of assigned service units exist for the service group, 
              if the number of instantiated service units is large enough. This object
              is only applicable for N-way and N-WayActive redundancy models. 
              The configuration of this value is optional and the default value 
              is the preferred number of in-service SUs as designated by 
              saAmfSGNumPrefInserviceSUs."
         ::= { saAmfSGTableEntry 7 }

     saAmfSGMaxActiveSIsperSU OBJECT-TYPE 
         SYNTAX      Unsigned32(0..4294967295)
         MAX-ACCESS  read-create
         STATUS      current
         DESCRIPTION
             "The maximum number of Service Instances
              that can be assigned as active to
              a Service Unit. Not applicable for 2N & noRedundancy redmodel.
              The configuration of this object is optional and by default
              there is 'no limit' to the max number of active SIs per SU. 
              Writable only when saAmfSGRowStatus is not active."
         ::= { saAmfSGTableEntry 8 }

     saAmfSGMaxStandbySIsperSU OBJECT-TYPE 
         SYNTAX      Unsigned32(0..4294967295)
         MAX-ACCESS  read-create
         STATUS      current
         DESCRIPTION
             "The maximum number of Service Instances
              that can be assigned as standby to
              a Service Unit. Not applicable when
              saAmfSGRedModel is noRedundancy or 2N. 
              The configuration of this object is optional and by default
              there is 'no limit' to the max number of standby SIs per SU. 
              Writable only when saAmfSGRowStatus is not active."
         ::= { saAmfSGTableEntry 9 }

     saAmfSGAdminState OBJECT-TYPE 
         SYNTAX      INTEGER { locked(1), unlocked(2), shuttingdown(3) }
         MAX-ACCESS  read-create
         STATUS      current
         DESCRIPTION
             "The desired administrative status of this SG.
              Enables locking, unlocking or shutting down
              the SUs that comprise the SG"
         ::= { saAmfSGTableEntry 10 }

     saAmfSGCompRestartProb OBJECT-TYPE 
         SYNTAX      SafTimeStamp
         MAX-ACCESS  read-create
         STATUS      current
         DESCRIPTION
             "The component restart probation period.
              The value is in units of
              nano seconds. The minimum
              value is 10 milli seconds(10000000)."
         ::= { saAmfSGTableEntry 11 }


     saAmfSGCompRestartMax OBJECT-TYPE 
         SYNTAX      Unsigned32(1..4294967295)
         MAX-ACCESS  read-create
         STATUS      current
         DESCRIPTION
             "The maximum number of times a component
              can restart within the probation time,
              without causing a error escalation."
         ::= { saAmfSGTableEntry 12 }


     saAmfSGSuRestartProb OBJECT-TYPE 
         SYNTAX      SafTimeStamp
         MAX-ACCESS  read-create
         STATUS      current
         DESCRIPTION
             "The service unit restart
              probation period. The value
              is in units of
              nano seconds. The minimum
              value is 10 milli seconds(10000000)."
         ::= { saAmfSGTableEntry 13 }


     saAmfSGSuRestartMax OBJECT-TYPE 
         SYNTAX      Unsigned32(1..4294967295)
         MAX-ACCESS  read-create
         STATUS      current
         DESCRIPTION
             "The maximum number of times a
              Service unit can restart within
              the probation time, without
              causing an SU failover."
         ::= { saAmfSGTableEntry 14 }

     saAmfSGNumCurrAssignedSU OBJECT-TYPE 
         SYNTAX      Counter32
         MAX-ACCESS  read-only
         STATUS      current
         DESCRIPTION
             "Denotes the number of Service Units
              that have Service instances
              assigned to them in the Service Group."
         ::= { saAmfSGTableEntry 15 }

     saAmfSGNumCurrNonInstantiatedSpareSU OBJECT-TYPE 
         SYNTAX      Counter32
         MAX-ACCESS  read-only
         STATUS      current
         DESCRIPTION
             "Denotes the number of Service Units
              currently configured in this
              Service Group but not yet instantiated."
         ::= { saAmfSGTableEntry 16 }

     saAmfSGNumCurrSpareSU OBJECT-TYPE 
         SYNTAX      Counter32
         MAX-ACCESS  read-only
         STATUS      current
         DESCRIPTION
             "Denotes the number of Service Units
              currently instantiated in this
              Service Group but not yet assigned
              a Service instance."
         ::= { saAmfSGTableEntry 17 }

     saAmfSGRowStatus OBJECT-TYPE 
         SYNTAX      RowStatus
         MAX-ACCESS  read-create
         STATUS      current
         DESCRIPTION
             "This variable is used to create, modify, and/or delete a row in
              this table. saAmfSGRedModel,saAmfSGNumPrefActiveSUs(for nPlusM) 
              saAmfSGNumPrefStandbySUs(for nPlusM),saAmfSGCompRestartProb,
              saAmfSGSuRestartMax, saAmfSGNumPrefInserviceSUs, saAmfSGNumPrefAssignedSUs, 
              saAmfSGMaxActiveSIsperSU (for nPlusM, nWay, nWayActive),
              saAmfSGSuRestartProb, saAmfSGMaxStandbySIsperSU (for nPlusM, nWay, nWayActive),
              saAmfSGCompRestartMax objects need to be set to valid values (except if they are optional) 
              to make the status active. This can be set to delete or not-in-service only 
              after all the dependent SUs, SIs and components are deleted and the 
              saAmfSGAdminState is set to locked"
         ::= { saAmfSGTableEntry 18 }


     --****************************************************************
     -- AMF Service Unit Table Objects
     --****************************************************************
          
     saAmfSUTable OBJECT-TYPE
         SYNTAX      SEQUENCE OF SaAmfSUTableEntry
         MAX-ACCESS  not-accessible
         STATUS      current
         DESCRIPTION
             "The Service Unit (SU) Table identifies
              all SUs that are configured in the
              cluster, each having a unique SU-name."
              
         ::= { saAmfTables 3 }

     saAmfSUTableEntry OBJECT-TYPE
         SYNTAX      SaAmfSUTableEntry
         MAX-ACCESS  not-accessible
         STATUS      current
         DESCRIPTION
             "An entry in this table represents an
              SU in the AMF Cluster."
         INDEX       {  saAmfSUName  }
         ::= { saAmfSUTable 1 }

     SaAmfSUTableEntry ::= SEQUENCE {
         saAmfSUName                             SnmpAdminString,
         saAmfSURank                             Unsigned32,  
         saAmfSUNumComponents                    Unsigned32, 
         saAmfSUNumCurrActiveSIs                 Counter32,
         saAmfSUNumCurrStandbySIs                Counter32,
         saAmfSUAdminState                       INTEGER,
         saAmfSUFailOver                         TruthValue,
         saAmfSUReadinessState                   INTEGER,
         saAmfSUOperState                        INTEGER,
         saAmfSUPresenceState                    INTEGER,
         saAmfSUPreInstantiable                  TruthValue,              
         saAmfSUParentSGName                     SnmpAdminString,
         saAmfSUIsExternal                       TruthValue,
         saAmfSURowStatus                        RowStatus
     }

     saAmfSUName OBJECT-TYPE 
         SYNTAX      SnmpAdminString
         MAX-ACCESS  accessible-for-notify
         STATUS      current
         DESCRIPTION
             "An octet string that uniquely identifies a
              Service Unit within the scope of a cluster"
         ::= { saAmfSUTableEntry 1 }


     saAmfSURank OBJECT-TYPE 
         SYNTAX      Unsigned32(1..4294967295)
         MAX-ACCESS  read-create
         STATUS      current
         DESCRIPTION
             "The rank of the Service Unit in the
              Service Group that determines the
              HA state of the Service instance
              assignments. Writable only when
              saAmfSURowStatus is not active"
         ::= { saAmfSUTableEntry 2 }

     saAmfSUNumComponents OBJECT-TYPE 
         SYNTAX      Unsigned32(1..4294967295)
         MAX-ACCESS  read-create
         STATUS      current
         DESCRIPTION
             "The number of components that
              make up this SU. Writable only
              when saAmfSURowStatus is not active"
         ::= { saAmfSUTableEntry 3 }

     saAmfSUNumCurrActiveSIs OBJECT-TYPE 
         SYNTAX      Counter32
         MAX-ACCESS  read-only
         STATUS      current
         DESCRIPTION
             "The current number of Service Instances
              that are assigned as active to this
              Service Unit"
         ::= { saAmfSUTableEntry 4 }

     saAmfSUNumCurrStandbySIs OBJECT-TYPE 
         SYNTAX      Counter32
         MAX-ACCESS  read-only
         STATUS      current
         DESCRIPTION
             "The current number of Service Instances
              that are assigned as standby to this
              Service Unit"
         ::= { saAmfSUTableEntry 5 }

     saAmfSUAdminState OBJECT-TYPE 
         SYNTAX      INTEGER { locked(1), unlocked(2), shuttingdown(3) }
         MAX-ACCESS  read-create
         STATUS      current
         DESCRIPTION
             "The desired administrative status
              of this SU. Enables locking,
              unlocking or shutting down of the SU"
         ::= { saAmfSUTableEntry 6 }

     saAmfSUFailOver OBJECT-TYPE 
         SYNTAX      TruthValue
         MAX-ACCESS  read-create
         STATUS      current
         DESCRIPTION
             "When this object is set to true, the
              failover will done for the entire SU,
              even if the component recommends component
              failover. Default value is true."
         ::= { saAmfSUTableEntry 7 }

     saAmfSUReadinessState OBJECT-TYPE 
         SYNTAX      INTEGER { outOfService(1), inService(2), stopping(3) }
         MAX-ACCESS  read-only
         STATUS      current
         DESCRIPTION
             "This value Indicates the Readiness
              State of the Service Unit"
         ::= { saAmfSUTableEntry 8 }

     saAmfSUOperState OBJECT-TYPE 
         SYNTAX      INTEGER {enabled(1), disabled(2)}
         MAX-ACCESS  read-only
         STATUS      current
         DESCRIPTION
             "Indicates the operational
              State of the Service Unit."
         ::= { saAmfSUTableEntry 9 }

     saAmfSUPresenceState OBJECT-TYPE 
         SYNTAX      INTEGER {saAmfUninstantiated(1),
                              saAmfInstantiating(2),
                              saAmfInstantiated(3),
                              saAmfTerminating(4),
                              saAmfRestarting(5),
                              saAmfInstantiationFailed(6),
                              saAmfTerminationFailed(7)}
         MAX-ACCESS  read-only
         STATUS      current
         DESCRIPTION
             "Indicates the presence
              State of the Service Unit."
         ::= { saAmfSUTableEntry 10 }

     saAmfSUPreInstantiable OBJECT-TYPE 
         SYNTAX      TruthValue
         MAX-ACCESS  read-only
         STATUS      current
         DESCRIPTION
             "This object indicates if the
              SU is pre-instantiable SU or not."
         ::= { saAmfSUTableEntry 11 }

     saAmfSUParentSGName OBJECT-TYPE 
         SYNTAX      SnmpAdminString
         MAX-ACCESS  read-create
         STATUS      current
         DESCRIPTION
             "This object indicates the name of
              the parent Service Group to which 
              this SU belongs. This object needs
              to be set before the saAmfSURowStatus
              can be made active.
              Writable only when
              saAmfSURowStatus is not active"
         ::= { saAmfSUTableEntry 12 }

     saAmfSUIsExternal OBJECT-TYPE 
         SYNTAX        TruthValue
         MAX-ACCESS    read-only
         STATUS        current
         DESCRIPTION
             "This object indicates if this SU is 'external'."
         ::= { saAmfSUTableEntry 13 }

     saAmfSURowStatus OBJECT-TYPE 
         SYNTAX      RowStatus
         MAX-ACCESS  read-create
         STATUS      current
         DESCRIPTION
             "This variable is used to create,
              modify, and/or delete a row in
              this table. saAmfSURank, 
              saAmfSUNumComponents, saAmfSUParentSGName 
              objects need to be set to valid
              values to make the status active.This
              can be set to delete or not in
              service only after all the dependent
              components, as well as entries in the 
              saAmfSUsperSIRankTable containing this SU 
              are deleted and the saAmfSUAdminState 
              is locked for the SU."
         ::= { saAmfSUTableEntry 14 }



     --****************************************************************
     -- AMF Service Instance  Table Objects
     --****************************************************************

          
     saAmfSITable OBJECT-TYPE
         SYNTAX      SEQUENCE OF SaAmfSITableEntry
         MAX-ACCESS  not-accessible
         STATUS      current
         DESCRIPTION
             "The Service Instance (SI) Table identifies
              all SIs that are configured in the
              cluster, each having a
              unique SI-name."
              
         ::= { saAmfTables 4 }

     saAmfSITableEntry OBJECT-TYPE
         SYNTAX      SaAmfSITableEntry
         MAX-ACCESS  not-accessible
         STATUS      current
         DESCRIPTION
             "An entry in this table represents an
              SI in the AMF Cluster."
         INDEX       {  saAmfSIName  }
         ::= { saAmfSITable 1 }

     SaAmfSITableEntry ::= SEQUENCE {
         saAmfSIName                             SnmpAdminString,
         saAmfSIRank                             Unsigned32,
         saAmfSINumCSIs                          Unsigned32,                                                 
         saAmfSIPrefNumAssignments               Unsigned32,
         saAmfSIAdminState                       INTEGER,
         saAmfSIOperState                        INTEGER, 
         saAmfSINumCurrActiveAssignments         Counter32,
         saAmfSINumCurrStandbyAssignments        Counter32,
         saAmfSIParentSGName                     SnmpAdminString,
         saAmfSIRowStatus                        RowStatus
     }

     saAmfSIName OBJECT-TYPE 
         SYNTAX      SnmpAdminString
         MAX-ACCESS  accessible-for-notify
         STATUS      current
         DESCRIPTION
             "An octet string that
              uniquely identifies a
              Service instance."
         ::= { saAmfSITableEntry 1 }

     saAmfSIRank OBJECT-TYPE 
         SYNTAX      Unsigned32(1..4294967295)
         MAX-ACCESS  read-create
         STATUS      current
         DESCRIPTION
             "The rank of the Service Instance 
              in the Service Group that 
              determines based on the SU
              availability if this SI will be
              assigned to SUs or not."
         ::= { saAmfSITableEntry 2 }

     saAmfSINumCSIs OBJECT-TYPE 
         SYNTAX      Unsigned32(1..4294967295)
         MAX-ACCESS  read-create
         STATUS      current
         DESCRIPTION
             "The number of CSIs that
              make up this SI.
              Writable only when
              saAmfSIAdminState is locked."
         ::= { saAmfSITableEntry 3 }

     saAmfSIPrefNumAssignments OBJECT-TYPE 
         SYNTAX      Unsigned32(1..4294967295)
         MAX-ACCESS  read-create
         STATUS      current
         DESCRIPTION "This object covers 'Preferred number of active 
                      assignment per SI' in N-Way active and 'Preferred 
                      number of standby assignments per SI'in N-Way 
                      redundancy model"
         ::= { saAmfSITableEntry 4 }

     saAmfSIAdminState OBJECT-TYPE 
         SYNTAX      INTEGER { locked(1), unlocked(2), shuttingdown(3) }
         MAX-ACCESS  read-create
         STATUS      current
         DESCRIPTION
             "The desired administrative status
              of this SI. Enables locking,
              unlocking or shutting down of the SI"
         ::= { saAmfSITableEntry 5 }

     saAmfSIOperState OBJECT-TYPE 
         SYNTAX      INTEGER {enabled(1), disabled(2)}
         MAX-ACCESS  read-only
         STATUS      current
         DESCRIPTION
             "Indicates the operational
              State of the Service Instance."
         ::= { saAmfSITableEntry 6 }

     saAmfSINumCurrActiveAssignments OBJECT-TYPE 
         SYNTAX      Counter32
         MAX-ACCESS  read-only
         STATUS      current
         DESCRIPTION
             "This value denotes The current number
              of active SU assignments this SI has 
              when the redundancy model of the SG is 
              nWayActive."
         ::= { saAmfSITableEntry 7 }

     saAmfSINumCurrStandbyAssignments OBJECT-TYPE 
         SYNTAX      Counter32
         MAX-ACCESS  read-only
         STATUS      current
         DESCRIPTION
             "This value denotes The current number
              of standby SU assignments this SI has
              when the redundancy model of the SG is
              nWay."
         ::= { saAmfSITableEntry 8 }

     saAmfSIParentSGName OBJECT-TYPE 
         SYNTAX      SnmpAdminString
         MAX-ACCESS  read-create
         STATUS      current
         DESCRIPTION
             "This value denotes the name of the
              Parent SG to which this SI belongs.
              Writable only when saAmfSIRowStatus
              is not active"
         ::= { saAmfSITableEntry 9 }

     saAmfSIRowStatus OBJECT-TYPE 
         SYNTAX      RowStatus
         MAX-ACCESS  read-create
         STATUS      current
         DESCRIPTION
             "This variable is used to create,
              modify, and/or delete a row in
              this table. saAmfSIRank, 
              saAmfSIPrefNumAssignments, 
              saAmfSINumCSIs and saAmfSIParentSGName 
              objects need to be set to valid
              values to make the status active.This
              can be set to delete or not-in-service
              only after all the dependent CSIs are deleted, 
              all the saAmfSISIDepTableEntry entries 
              corresponding to this SI are deleted, all 
              entries in the saAmfSUsperSIRankTable containing 
              this SI as the index are deleted and the 
              saAmfSIAdminState is locked for the SI."
         ::= { saAmfSITableEntry 10 }



     --********************************************************************
     -- saAmfSUsperSIRankTable table enables an administrator to configure 
     -- ranked SUs per SI as required by the nWay & nWayActive Redundancy Models.  
     --********************************************************************* 


     saAmfSUsperSIRankTable OBJECT-TYPE
         SYNTAX      SEQUENCE OF SaAmfSUsperSIRankEntry
         MAX-ACCESS  not-accessible
         STATUS      current
         DESCRIPTION
             " This table enables adminstrators to configure ranked
               SUs per SI for a particular SG when the redundancy model
               of the SG is either nWay or nWayActive. There will be no entries in this
               table if the SG redundancy model is not nWay or nWayActive."
              
         ::= { saAmfTables 5 }

     saAmfSUsperSIRankEntry OBJECT-TYPE
         SYNTAX      SaAmfSUsperSIRankEntry
         MAX-ACCESS  not-accessible
         STATUS      current
         DESCRIPTION
             "An entry in this table represents an
              SI-SU ranked order value."
         INDEX       {  saAmfSUsperSIName, saAmfSUsperSIRank }
         ::= { saAmfSUsperSIRankTable 1 }


     SaAmfSUsperSIRankEntry ::= SEQUENCE {
         saAmfSUsperSIName        SnmpAdminString,
         saAmfSUsperSIRank        Unsigned32,
         saAmfSUsperSISUName      SnmpAdminString,
         saAmfSUsperSIRowStatus   RowStatus
     }

     saAmfSUsperSIName OBJECT-TYPE 
         SYNTAX        SnmpAdminString
         MAX-ACCESS    accessible-for-notify
         STATUS        current
         DESCRIPTION
             "An octet string that uniquely identifies a
              Service instance which is being configured with ranked
              SUs."
         ::= { saAmfSUsperSIRankEntry 1 }


      saAmfSUsperSIRank OBJECT-TYPE 
         SYNTAX         Unsigned32
         MAX-ACCESS     accessible-for-notify
         STATUS         current
         DESCRIPTION    "The rank of the SU for the SI 
                         designated by saAmfSUsperSIName."
         ::= { saAmfSUsperSIRankEntry 2 }


      saAmfSUsperSISUName OBJECT-TYPE 
         SYNTAX           SnmpAdminString
         MAX-ACCESS       read-create
         STATUS           current
         DESCRIPTION
             "An octet string that uniquely identifies a
              Service Unit which is being configured with rank
              designated by saAmfSUsperSIRank for the SI designated
              by saAmfSUsperSIName."
         ::= { saAmfSUsperSIRankEntry 3 }

      saAmfSUsperSIRowStatus OBJECT-TYPE 
         SYNTAX              RowStatus
         MAX-ACCESS          read-create
         STATUS              current
         DESCRIPTION
             "This variable is used to create,
              modify, and/or delete a row in
              this table. saAmfSUsperSISUName
              object needs to be set to a valid value
              to make the status active.
              This variable can be set to destroy or notinservice only if the
              adminstate of the SI designated by saAmfSUsperSIName and the SU 
              designated by saAmfSUsperSISUName columnar value is LOCKED. 
              No object in this table should be modified
              when the value of rowstatus is active."
         ::= { saAmfSUsperSIRankEntry 4 }


     --*********************************************************************
     -- AMF SG-SI-Rank table. This is a read-only table that enables
     -- an administrator to view an ordered list of SIs per SG based on rank
     --*********************************************************************
     saAmfSGSIRankTable OBJECT-TYPE
         SYNTAX      SEQUENCE OF SaAmfSGSIRankEntry
         MAX-ACCESS  not-accessible
         STATUS      current
         DESCRIPTION
             " This is a read-only table that enables an administrator
               to view the ordered list of SIs per SG based on rank."
         ::= { saAmfTables 6 }

     saAmfSGSIRankEntry OBJECT-TYPE
         SYNTAX      SaAmfSGSIRankEntry
         MAX-ACCESS  not-accessible
         STATUS      current
         DESCRIPTION
             "An entry in this table represents an
              SG-SI ranked order value."
         INDEX       {  saAmfSGSIRankSGName, saAmfSGSIRank}
         ::= { saAmfSGSIRankTable 1 }


      SaAmfSGSIRankEntry ::= SEQUENCE {
         saAmfSGSIRankSGName      SnmpAdminString,
         saAmfSGSIRank            Unsigned32,
         saAmfSGSIRankSIName      SnmpAdminString
      }

      saAmfSGSIRankSGName OBJECT-TYPE 
         SYNTAX           SnmpAdminString
         MAX-ACCESS       accessible-for-notify
         STATUS            current
         DESCRIPTION
             "An octet string that uniquely identifies a
              Service Group which is being configured with ranked
              SIs."
         ::= { saAmfSGSIRankEntry 1 }


      saAmfSGSIRank     OBJECT-TYPE 
         SYNTAX         Unsigned32
         MAX-ACCESS     accessible-for-notify
         STATUS         current
         DESCRIPTION    "The rank of the SI for the SG 
                         designated by saAmfSGSIRankSGName."
         ::= { saAmfSGSIRankEntry 2 }


      saAmfSGSIRankSIName OBJECT-TYPE 
         SYNTAX           SnmpAdminString
         MAX-ACCESS       read-create
         STATUS           current
         DESCRIPTION
             "An octet string that uniquely identifies a
              Service Instance which is being configured with rank
              designated by saAmfSGSIRank for the SG designated
              by saAmfSGSIRankSGName."
         ::= { saAmfSGSIRankEntry 3 }




     --*********************************************************************
     -- AMF SG-SU-Rank table. This is a read-only table that enables 
     -- an administrator to view an ordered list of SUs per SG based on rank
     --*********************************************************************

     saAmfSGSURankTable OBJECT-TYPE
         SYNTAX      SEQUENCE OF SaAmfSGSURankEntry
         MAX-ACCESS  not-accessible
         STATUS      current
         DESCRIPTION
             " This is a read-only table that enables an administrator
               to view the ordered list of SUs per SG based on rank."
         ::= { saAmfTables 7 }

     saAmfSGSURankEntry OBJECT-TYPE
         SYNTAX      SaAmfSGSURankEntry
         MAX-ACCESS  not-accessible
         STATUS      current
         DESCRIPTION
             "An entry in this table represents an
              SG-SU ranked order value."
         INDEX       {  saAmfSGSURankSGName, saAmfSGSURank}
         ::= { saAmfSGSURankTable 1 }


      SaAmfSGSURankEntry ::= SEQUENCE {
         saAmfSGSURankSGName      SnmpAdminString,
         saAmfSGSURank            Unsigned32,
         saAmfSGSURankSUName      SnmpAdminString
      }

      saAmfSGSURankSGName OBJECT-TYPE 
         SYNTAX           SnmpAdminString
         MAX-ACCESS       accessible-for-notify
         STATUS            current
         DESCRIPTION
             "An octet string that uniquely identifies a
              Service Group which is being configured with ranked
              SIs."
         ::= { saAmfSGSURankEntry 1 }


      saAmfSGSURank     OBJECT-TYPE 
         SYNTAX         Unsigned32
         MAX-ACCESS     accessible-for-notify
         STATUS         current
         DESCRIPTION    "The rank of the SU for the SG 
                         designated by saAmfSGSURankSGName."
         ::= { saAmfSGSURankEntry 2 }


      saAmfSGSURankSUName OBJECT-TYPE 
         SYNTAX           SnmpAdminString
         MAX-ACCESS       read-create
         STATUS           current
         DESCRIPTION
             "An octet string that uniquely identifies a
              Service Unit which is being configured with rank
              designated by saAmfSGSURank for the SG designated
              by saAmfSGSURankSGName."
         ::= { saAmfSGSURankEntry 3 }



     --****************************************************************
     -- AMF Service Instance dependencies Table Objects
     --****************************************************************

          
     saAmfSISIDepTable OBJECT-TYPE
         SYNTAX      SEQUENCE OF SaAmfSISIDepTableEntry
         MAX-ACCESS  not-accessible
         STATUS      current
         DESCRIPTION
             "The Service Instance-Service Instance (SI-SI)
              dependency Table identifies the dependencies
              between SIs that are configured in the
              saAmfSITable."
              
         ::= { saAmfTables 8 }

     saAmfSISIDepTableEntry OBJECT-TYPE
         SYNTAX      SaAmfSISIDepTableEntry
         MAX-ACCESS  not-accessible
         STATUS      current
         DESCRIPTION
             "An entry in this table represents an
              SI-SI dependency in the AMF Cluster."
         INDEX       {  saAmfSISIDepSIName , saAmfSISIDepDepndSIName }
         ::= { saAmfSISIDepTable 1 }

     SaAmfSISIDepTableEntry ::= SEQUENCE {
         saAmfSISIDepSIName                      SnmpAdminString,
         saAmfSISIDepDepndSIName                 SnmpAdminString,
         saAmfSISIDepToltime                     SafTimeStamp,
         saAmfSISIDepRowStatus                   RowStatus
     }

     saAmfSISIDepSIName OBJECT-TYPE 
         SYNTAX      SnmpAdminString
         MAX-ACCESS  accessible-for-notify
         STATUS      current
         DESCRIPTION
             "An octet string that uniquely identifies a
              Service instance for which saAmfSIRowStatus
              is active."
         ::= { saAmfSISIDepTableEntry 1 }

     saAmfSISIDepDepndSIName OBJECT-TYPE 
         SYNTAX      SnmpAdminString
         MAX-ACCESS  accessible-for-notify
         STATUS      current
         DESCRIPTION
             "An octet string that uniquely identifies a
              Service instance for which saAmfSIRowStatus
              is active. This SI is dependent on the 
              saAmfSISIDepSIName to be enabled for it
              to be enabled."
         ::= { saAmfSISIDepTableEntry 2 }
         
     saAmfSISIDepToltime OBJECT-TYPE 
         SYNTAX      SafTimeStamp
         MAX-ACCESS  read-create
         STATUS      current
         DESCRIPTION
             "The amount of time AMF waits in nano-seconds 
              to disable saAmfSISIDepDepndSIName SI, if 
              saAmfSISIDepSIName SI becomes disabled."
         ::= { saAmfSISIDepTableEntry 3 }

     saAmfSISIDepRowStatus OBJECT-TYPE 
         SYNTAX      RowStatus
         MAX-ACCESS  read-create
         STATUS      current
         DESCRIPTION
             "This variable is used to create,
              modify, and/or delete a row in
              this table. saAmfSISIDepToltime
              needs to be set to valid
              value to make the status active."
         ::= { saAmfSISIDepTableEntry 4 }

     --****************************************************************
     -- AMF Component  Table Objects
     --****************************************************************
          
     saAmfCompTable OBJECT-TYPE
         SYNTAX      SEQUENCE OF SaAmfCompTableEntry
         MAX-ACCESS  not-accessible
         STATUS      current
         DESCRIPTION
             "The Component Table identifies
              all Components that are configured in the
              cluster, each having a
              unique component-name."
              
         ::= { saAmfTables 9 }

     saAmfCompTableEntry OBJECT-TYPE
         SYNTAX      SaAmfCompTableEntry
         MAX-ACCESS  not-accessible
         STATUS      current
         DESCRIPTION
             "An entry in this table represents a 
              component in the AMF cluster"
         INDEX       {  saAmfCompName  }
         ::= { saAmfCompTable 1 }

     SaAmfCompTableEntry ::= SEQUENCE {
         saAmfCompName                                  SnmpAdminString,
         saAmfCompCapability                            SafAmfCompCapabilityModel,
         saAmfCompCategory                              INTEGER,
         saAmfCompInstantiateCmd                        DisplayString,
         saAmfCompTerminateCmd                          DisplayString,
         saAmfCompCleanupCmd                            DisplayString,
         saAmfCompAmStartCmd                            DisplayString,
         saAmfCompAmStopCmd                             DisplayString,
         saAmfCompInstantiationLevel                    Unsigned32,
         saAmfCompInstantiateTimeout                    SafTimeStamp,
         saAmfCompDelayBetweenInstantiateAttempts       SafTimeStamp,
         saAmfCompTerminateTimeout                      SafTimeStamp,
         saAmfCompCleanupTimeout                        SafTimeStamp,
         saAmfCompAmStartTimeout                        SafTimeStamp,
         saAmfCompAmStopTimeout                         SafTimeStamp,
         saAmfCompTerminateCallbackTimeOut              SafTimeStamp,
         saAmfCompCSISetCallbackTimeout                 SafTimeStamp,
         saAmfCompQuiescingCompleteTimeout              SafTimeStamp,
         saAmfCompCSIRmvCallbackTimeout                 SafTimeStamp,
         saAmfCompProxiedCompInstantiateCallbackTimeout SafTimeStamp,
         saAmfCompProxiedCompCleanupCallbackTimeout     SafTimeStamp,
         saAmfCompNodeRebootCleanupFail                 TruthValue,
         saAmfCompRecoveryOnError                       SafAmfRecommendedRecovery,
         saAmfCompNumMaxInstantiate                     Unsigned32,
         saAmfCompNumMaxInstantiateWithDelay            Unsigned32,
         saAmfCompNumMaxAmStartAttempts                 Unsigned32,
         saAmfCompNumMaxAmStopAttempts                  Unsigned32,
         saAmfCompDisableRestart                        TruthValue,
         saAmfCompNumMaxActiveCsi                       Unsigned32,
         saAmfCompNumMaxStandbyCsi                      Unsigned32,    
         saAmfCompNumCurrActiveCsi                      Counter32,
         saAmfCompNumCurrStandbyCsi                     Counter32,
         saAmfCompRestartCount                          Counter32,
         saAmfCompOperState                             INTEGER,
         saAmfCompPresenceState                         INTEGER,
         saAmfCompReadinessState                        INTEGER,
         saAmfCompCurrProxyName                         SnmpAdminString,
         saAmfCompAMEnable                              INTEGER,
         saAmfCompRowStatus                             RowStatus
     }

     saAmfCompName OBJECT-TYPE 
         SYNTAX      SnmpAdminString
         MAX-ACCESS  accessible-for-notify
         STATUS      current
         DESCRIPTION
             "An octet string that
              uniquely identifies a component"
         ::= { saAmfCompTableEntry 1 }

     saAmfCompCapability OBJECT-TYPE 
         SYNTAX      SafAmfCompCapabilityModel
         MAX-ACCESS  read-create
         STATUS      current
         DESCRIPTION
             "This value denotes the Capability
              of the component as defined by
              SAFs Component Capability Model.
              Writable only when
              saAmfCompRowStatus is not active"
         ::= { saAmfCompTableEntry 2 }

     saAmfCompCategory OBJECT-TYPE 
         SYNTAX      INTEGER { saAware(0),
                               proxiedLocalPreinstantiable(1),
                               proxiedLocalNonPreinstantiable(2),
                               externalPreinstantiable(3),	
                               externalNonPreinstantiable(4),
                               unproxiedNonSaAware(5)  }
         MAX-ACCESS  read-create
         STATUS      current
         DESCRIPTION
             "This value denotes the component type.
              External components are always proxied, therefore the
              'proxied' word has been left out in order to restrict 
              the identifier's length. Writable only when
              saAmfCompRowStatus is not active"
         ::= { saAmfCompTableEntry 3 }

     saAmfCompInstantiateCmd OBJECT-TYPE 
         SYNTAX      DisplayString
         MAX-ACCESS  read-create
         STATUS      current
         DESCRIPTION
             "This value denotes the Instantiate
              command of the component. This command is not applicable for 
              components whose saAmfCompCategory value is either of the following...
              proxiedLocalPreinstantiable, proxiedLocalNonPreinstantiable,
              externalPreinstantiable and externalNonPreinstantiable."
         ::= { saAmfCompTableEntry 4 }

     saAmfCompTerminateCmd OBJECT-TYPE 
         SYNTAX      DisplayString
         MAX-ACCESS  read-create
          STATUS      current
         DESCRIPTION
             "This value denotes the Terminate
              script of the component. This
              command is applicable for 
              components with saAmfCompCategory value as
              unproxiedNonSaAware."
         ::= { saAmfCompTableEntry 5 }

     saAmfCompCleanupCmd OBJECT-TYPE 
         SYNTAX      DisplayString
         MAX-ACCESS  read-create
         STATUS      current
         DESCRIPTION
             "This value denotes the Cleanup
              command of the component."
         ::= { saAmfCompTableEntry 6 }

     saAmfCompAmStartCmd OBJECT-TYPE 
         SYNTAX      DisplayString
         MAX-ACCESS  read-create
         STATUS      current
         DESCRIPTION
             "This value denotes the Application Monitor 
              Start command of the component."
         ::= { saAmfCompTableEntry 7 }

     saAmfCompAmStopCmd OBJECT-TYPE 
         SYNTAX      DisplayString
         MAX-ACCESS  read-create
         STATUS      current
         DESCRIPTION
             "This value denotes the Application Monitor
              Stop command of the component."
         ::= { saAmfCompTableEntry 8 }

     saAmfCompInstantiationLevel OBJECT-TYPE 
         SYNTAX      Unsigned32(1..4294967295)
         MAX-ACCESS  read-create
         STATUS      current
         DESCRIPTION
             "This value determines the order in which
              components in an SU are instantiated and 
              terminated. This object is aplicable only
              for pre-instantiable components.
              Writable only when
              saAmfCompRowStatus is not active"
         ::= { saAmfCompTableEntry 9 }

     saAmfCompInstantiateTimeout OBJECT-TYPE 
         SYNTAX      SafTimeStamp
         MAX-ACCESS  read-create
         STATUS      current
         DESCRIPTION
             "Time in nano-seconds in which the AMF 
              expects the instantiate command to
              complete and the component registers
              with AMF by calling saAmfComponentRegister
              API. A value of 0 means that the AMF 
              should use a default value instead."
         ::= { saAmfCompTableEntry 10 }

     saAmfCompDelayBetweenInstantiateAttempts OBJECT-TYPE 
         SYNTAX      SafTimeStamp
         MAX-ACCESS  read-create
         STATUS      current
         DESCRIPTION
             "Time in nano-seconds, is the delay
              period AMF waits before attempting 
              to instantiate a component after 
              failing to instantiate it within
              saAmfCompNumMaxInstantiate attempts.
              A value of 0 means that the AMF 
              should use a default value instead."
         ::= { saAmfCompTableEntry 11 }          

     saAmfCompTerminateTimeout OBJECT-TYPE 
         SYNTAX      SafTimeStamp
         MAX-ACCESS  read-create
         STATUS      current
         DESCRIPTION
             "Time in nano-seconds in which the AMF expects 
              the terminate CLC-CLI command to return success. 
              A value of 0 means that the AMF should use a 
              default value instead. If a component has not 
              responded within saAmfCompTerminateTimeout 
              it will be shut down by executing the cleanup command"
         ::= { saAmfCompTableEntry 12 }

     saAmfCompCleanupTimeout OBJECT-TYPE 
         SYNTAX      SafTimeStamp
         MAX-ACCESS  read-create
         STATUS      current
         DESCRIPTION
             "Time in nano-seconds in which the AMF expects 
              the cleanup CLC-CLI command to return success. 
              A value of 0 means that the AMF should use a 
              default value instead. "
         ::= { saAmfCompTableEntry 13 }

     saAmfCompAmStartTimeout OBJECT-TYPE 
         SYNTAX      SafTimeStamp
         MAX-ACCESS  read-create
         STATUS      current
         DESCRIPTION
             "Time in nano-seconds in which the AMF 
              expects the AM_START command to
              complete. A value of 0 means that the AMF 
              should use a default value instead."
         ::= { saAmfCompTableEntry 14 }     

     saAmfCompAmStopTimeout OBJECT-TYPE 
         SYNTAX      SafTimeStamp
         MAX-ACCESS  read-create
         STATUS      current
         DESCRIPTION
             "Time in nano-seconds in which the AMF 
              expects the AM_STOP command to
              complete. A value of 0 means that the AMF 
              should use a default value instead."
         ::= { saAmfCompTableEntry 15 }

     saAmfCompTerminateCallbackTimeOut OBJECT-TYPE 
         SYNTAX      SafTimeStamp
         MAX-ACCESS  read-create
         STATUS      current
         DESCRIPTION
             "Time in nano-seconds in which the AMF expects an 
              SaAmfResponse call from the component after a preceding 
              callback initiation. A value of 0 means that the AMF 
              should use a default value instead."
         ::= { saAmfCompTableEntry 16 }

     saAmfCompCSISetCallbackTimeout OBJECT-TYPE 
         SYNTAX      SafTimeStamp
         MAX-ACCESS  read-create
         STATUS      current
         DESCRIPTION
             "Time in nano-seconds in which the AMF expects an 
              SaAmfResponse call from the component after a preceding 
              CSI set callback initiation. A value of 0 means that the AMF 
              should use a default value instead."
         ::= { saAmfCompTableEntry 17 }

     saAmfCompQuiescingCompleteTimeout OBJECT-TYPE 
         SYNTAX      SafTimeStamp
         MAX-ACCESS  read-create
         STATUS      current
         DESCRIPTION
             "Time in nano-seconds in which the AMF expects an 
              saAmfCSIQuiescingComplete() call from the component after a preceding 
              CSI set callback initiation from active->quiescing HA state. 
              Note this is not a timeout for saAMFResponse().
              A value of 0 means that the AMF should use a default value instead."
         ::= { saAmfCompTableEntry 18 }

     saAmfCompCSIRmvCallbackTimeout OBJECT-TYPE 
         SYNTAX      SafTimeStamp
         MAX-ACCESS  read-create
         STATUS      current
         DESCRIPTION
             "Time in nano-seconds in which the AMF expects an 
              SaAmfResponse call from the component after a preceding 
              CSI Remove callback initiation. A value of 0 means that the AMF 
              should use a default value instead."
         ::= { saAmfCompTableEntry 19 }

     saAmfCompProxiedCompInstantiateCallbackTimeout OBJECT-TYPE 
         SYNTAX      SafTimeStamp
         MAX-ACCESS  read-create
         STATUS      current
         DESCRIPTION
             "Time in nano-seconds in which the AMF expects an 
              SaAmfResponse call from the component after a preceding 
              proxied component instantiate callback initiation. 
              A value of 0 means that the AMF should use a default 
              value instead."
         ::= { saAmfCompTableEntry 20 }

     saAmfCompProxiedCompCleanupCallbackTimeout OBJECT-TYPE 
         SYNTAX      SafTimeStamp
         MAX-ACCESS  read-create
         STATUS      current
         DESCRIPTION
             "Time in nano-seconds in which the AMF expects an 
              SaAmfResponse call from the component after a preceding 
              proxied component cleanup callback initiation. 
              A value of 0 means that the AMF should use a default 
              value instead."
         ::= { saAmfCompTableEntry 21 }


     saAmfCompNodeRebootCleanupFail OBJECT-TYPE 
         SYNTAX      TruthValue
         MAX-ACCESS  read-create
         STATUS      current
         DESCRIPTION
             "If set to TRUE on CLEANUP script failure AMF will
              do a node failover and node reboot. If false the
              SIs having CSIs assigned to this component will
              be unassigned."
         ::= { saAmfCompTableEntry 22 }

     saAmfCompRecoveryOnError OBJECT-TYPE 
         SYNTAX      SafAmfRecommendedRecovery
         MAX-ACCESS  read-create
         STATUS      current
         DESCRIPTION
             "Recommended Recovery configured per component to be engaged
              in the following cases:
               a) When saAmfComponentErrorReport is received with recommended recovery 
                  SA_AMF_NO_RECOMMENDATION.
               b) Timeouts for AMF callbacks.
               c) Error return codes from the application process, 
                  when a callback was invoked.
               d) There is a communication loss between the AMF Area server 
                  and the AMF library linked into a component.
                 
              The Recommended Recovery of a component can never be set to
              SA_AMF_NO_RECOMMENDATION."
         ::= { saAmfCompTableEntry 23 }

     saAmfCompNumMaxInstantiate OBJECT-TYPE 
         SYNTAX      Unsigned32(1..4294967295)
         MAX-ACCESS  read-create
         STATUS      current
         DESCRIPTION
             "This value denotes the maximum number of
              times AMF tries to instantiate the
              component if it fails during instatiation."
         ::= { saAmfCompTableEntry 24 }

     saAmfCompNumMaxInstantiateWithDelay OBJECT-TYPE 
         SYNTAX      Unsigned32(1..4294967295)
         MAX-ACCESS  read-create
         STATUS      current
         DESCRIPTION
             "This value denotes the maximum number of
              times AMF tries to instantiate the
              component with delay, if it fails to
              instatiate after saAmfCompNumMaxInstantiate
              retries. After the specified count it will place
              the components saAmfCompPresenceState in
              saAmfInstantiationFailed. If this object is not
              configured then it will show the value as 0,
              but value 0 can not be configured." 
         ::= { saAmfCompTableEntry 25 }

     saAmfCompNumMaxAmStartAttempts OBJECT-TYPE 
         SYNTAX      Unsigned32(1..4294967295)
         MAX-ACCESS  read-create
         STATUS      current
         DESCRIPTION
             "This value denotes the maximum number of
              times AMF tries to re issue the AM_START CLI
              command if it fails. "
         ::= { saAmfCompTableEntry 26 }

     saAmfCompNumMaxAmStopAttempts OBJECT-TYPE 
         SYNTAX      Unsigned32(1..4294967295)
         MAX-ACCESS  read-create
         STATUS      current
         DESCRIPTION
             "This value denotes the maximum number of
              times AMF tries to re issue the AM_STOP CLI
              command if it fails. If this object is not
              configured then it will show the value as 0,
              but value 0 can not be configured. "
         ::= { saAmfCompTableEntry 27 }

     saAmfCompDisableRestart OBJECT-TYPE 
         SYNTAX      TruthValue
         MAX-ACCESS  read-create
         STATUS      current
         DESCRIPTION
             "If set to TRUE, disables restarting
              the component as part of recovery.
              Writable only when saAmfCompRowStatus 
              is not active"
         ::= { saAmfCompTableEntry 28 }

     saAmfCompNumMaxActiveCsi OBJECT-TYPE 
         SYNTAX      Unsigned32(1..4294967295)
         MAX-ACCESS  read-create
         STATUS      current
         DESCRIPTION
             "This value denotes the maximum number of
              CSIs that can be assigned as active to
              this component. Aplicable only if
              saAmfCompCapability is xactiveandystandby
              xactiveorystandby,xactive. Writable only 
              when saAmfCompRowStatus is not active"
         ::= { saAmfCompTableEntry 29 }

     saAmfCompNumMaxStandbyCsi OBJECT-TYPE 
         SYNTAX      Unsigned32(1..4294967295)
         MAX-ACCESS  read-create
         STATUS      current
         DESCRIPTION
             "This value denotes the maximum number of
              CSIs that can be assigned as standby to
              this component. Aplicable only if
              saAmfCompCapability is xactiveandystandby
              xactiveorystandby,oneactiveorxstandby. 
              Writable only when saAmfCompRowStatus
              is not active."
         ::= { saAmfCompTableEntry 30 }

     saAmfCompNumCurrActiveCsi OBJECT-TYPE 
         SYNTAX      Counter32
         MAX-ACCESS  read-only
         STATUS      current
         DESCRIPTION
             "This value denotes the number of
              CSI relationships that have been
              assigned as active to this component."
         ::= { saAmfCompTableEntry 31 }

     saAmfCompNumCurrStandbyCsi OBJECT-TYPE 
         SYNTAX      Counter32
         MAX-ACCESS  read-only
         STATUS      current
         DESCRIPTION
             "This value denotes the number of
              CSI relationships that have been
              assigned as standby to this component."
         ::= { saAmfCompTableEntry 32 }

     saAmfCompRestartCount OBJECT-TYPE 
         SYNTAX      Counter32
         MAX-ACCESS  read-only
         STATUS      current
         DESCRIPTION
             "Indicates the number of component
              restarts."
         ::= { saAmfCompTableEntry 33 }

     saAmfCompOperState OBJECT-TYPE 
         SYNTAX      INTEGER {enabled(1), disabled(2)}
         MAX-ACCESS  read-only
         STATUS      current
         DESCRIPTION
             "Indicates the operational
              State of the component."
         ::= { saAmfCompTableEntry 34 }


     saAmfCompPresenceState OBJECT-TYPE 
         SYNTAX      INTEGER {saAmfUninstantiated(1),
                              saAmfInstantiating(2),
                              saAmfInstantiated(3),
                              saAmfTerminating(4),
                              saAmfRestarting(5),
                              saAmfInstantiationFailed(6),
                              saAmfTerminationFailed(7)}
         MAX-ACCESS  read-only
         STATUS      current
         DESCRIPTION
             "Indicates the presence
              State of the component."
         ::= { saAmfCompTableEntry 35 }

     saAmfCompReadinessState OBJECT-TYPE 
         SYNTAX      INTEGER { outOfService(1), inService(2), stopping(3) }
         MAX-ACCESS  read-only
         STATUS      current
         DESCRIPTION
             "This value Indicates the Readiness
              State of the component."
         ::= { saAmfCompTableEntry 36 }

     saAmfCompCurrProxyName OBJECT-TYPE 
         SYNTAX      SnmpAdminString
         MAX-ACCESS  read-only
         STATUS      current
         DESCRIPTION
             "This value denotes the proxy component
              that manages this component. This
              object is only applicable if component's 
              saAmfCompCategory is proxiedLocalPreinstantiable,
              proxiedLocalNonPreinstantiable, externalPreinstantiable
              or externalNonPreinstantiable. Writable                
              only when saAmfCompRowStatus is not active."
         ::= { saAmfCompTableEntry 37 }

     saAmfCompAMEnable OBJECT-TYPE 
        SYNTAX       INTEGER { enabled(1),  disabled(2) }
        MAX-ACCESS  read-create
        STATUS      current
        DESCRIPTION
            "This object is used to enable / disable active monitoring. It  
            is set only when AM_START and AM_STOP commands are configured."
        ::= { saAmfCompTableEntry 38 }

     saAmfCompRowStatus OBJECT-TYPE 
         SYNTAX      RowStatus
         MAX-ACCESS  read-create
         STATUS      current
         DESCRIPTION
             "This variable is used to create,
              modify, and/or delete a row in
              this table. 
              saAmfCompCapability
              saAmfCompCategory,saAmfCompInstantiateCmd,
              saAmfCompTerminateCmd,saAmfCompCleanupCmd,
              saAmfCompAmStartCmd,saAmfCompAmStopCmd,
              saAmfCompRecoveryOnError,
              saAmfCompNumMaxInstantiate,
              saAmfCompNumMaxActiveCsi, 
              saAmfCompNumMaxStandbyCsi 
              objects need to be set to valid
              values to make the status active.This
              can be set to delete or not in
              service only if the saAmfSUAdminState and
              saAmfSUPresenceState of the SU to which this
              component belongs are locked and 
              saAmfUninstantiated or saAmfTerminationFailed
              respectively."
         ::= { saAmfCompTableEntry 39 }

     --****************************************************************
     -- AMF Component-CompServiceType supported table. This tables 
     -- enables configuring various component services instance types 
     -- supported by a component on a per component basis.
     --****************************************************************
     saAmfCompCSTypeSupportedTable OBJECT-TYPE
         SYNTAX      SEQUENCE OF SaAmfCompCSTypeSupportedTableEntry
         MAX-ACCESS  not-accessible
         STATUS      current
         DESCRIPTION
             "The Component-CompServiceType supported table identifies
              all the CSI types each of the Components configured in the
              cluster support."
              
         ::= { saAmfTables 10 }

     saAmfCompCSTypeSupportedTableEntry OBJECT-TYPE
         SYNTAX      SaAmfCompCSTypeSupportedTableEntry
         MAX-ACCESS  not-accessible
         STATUS      current
         DESCRIPTION
             "An entry in this table represents a 
              CS Type supported by a component."
         INDEX   {  saAmfCompCSTypeSupportedCompName, saAmfCompCSTypeSupportedCSIName}
         ::= { saAmfCompCSTypeSupportedTable 1 }


     SaAmfCompCSTypeSupportedTableEntry ::= SEQUENCE {
         saAmfCompCSTypeSupportedCompName       SnmpAdminString,
         saAmfCompCSTypeSupportedCSIName        SnmpAdminString,
         saAmfCompCSTypeSupportedRowStatus      RowStatus
         }


     saAmfCompCSTypeSupportedCompName OBJECT-TYPE 
         SYNTAX      SnmpAdminString
         MAX-ACCESS  accessible-for-notify
         STATUS      current
         DESCRIPTION
             "An octet string that uniquely identifies a
              component name."
         ::= { saAmfCompCSTypeSupportedTableEntry 1 }

     saAmfCompCSTypeSupportedCSIName OBJECT-TYPE 
         SYNTAX      SnmpAdminString
         MAX-ACCESS  accessible-for-notify
         STATUS      current
         DESCRIPTION
             "An octet string that uniquely identifies a
              component service instance type name."
         ::= { saAmfCompCSTypeSupportedTableEntry 2 }

     saAmfCompCSTypeSupportedRowStatus OBJECT-TYPE 
         SYNTAX      RowStatus
         MAX-ACCESS  read-create
         STATUS      current
         DESCRIPTION
             "This variable is used to create,
              modify, and/or delete a row in
              this table."
         ::= { saAmfCompCSTypeSupportedTableEntry 3 }

     --****************************************************************
     -- AMF Component Service Instance  Table Objects
     --****************************************************************
          
     saAmfCSITable OBJECT-TYPE
         SYNTAX      SEQUENCE OF SaAmfCSITableEntry
         MAX-ACCESS  not-accessible
         STATUS      current
         DESCRIPTION
             "The CSI Table identifies
              all Component Service Instances (CSI)
              that are configured in the
              cluster, each having a
              unique CSI-name."
              
         ::= { saAmfTables 11 }

     saAmfCSITableEntry OBJECT-TYPE
         SYNTAX      SaAmfCSITableEntry
         MAX-ACCESS  not-accessible
         STATUS      current
         DESCRIPTION
             "An entry in this table represents a 
              CSI in the AMF cluster."
         INDEX       {  saAmfCSIName  }
         ::= { saAmfCSITable 1 }

     SaAmfCSITableEntry ::= SEQUENCE {
         saAmfCSIName            SnmpAdminString,
         saAmfCSType            SnmpAdminString,
         saAmfCSIRank            Unsigned32,
         saAmfCSIRowStatus       RowStatus    }
  
     saAmfCSIName OBJECT-TYPE 
         SYNTAX      SnmpAdminString
         MAX-ACCESS  accessible-for-notify
         STATUS      current
         DESCRIPTION
             "An octet string that uniquely identifies a
              component service instance name."
         ::= { saAmfCSITableEntry 1 }

     saAmfCSType OBJECT-TYPE 
         SYNTAX      SnmpAdminString
         MAX-ACCESS  read-create
         STATUS      current
         DESCRIPTION
             "This value is the  CS Type of
              this component service instance. 
              Writable only when
              saAmfCsiRowStatus is not active"
         ::= { saAmfCSITableEntry 2 }

     saAmfCSIRank OBJECT-TYPE 
         SYNTAX      Unsigned32(0..4294967295)
         MAX-ACCESS  read-create
         STATUS      current
         DESCRIPTION
             "This value determines the order
              in which the CSIs in a 
              service instance are assigned to
              components. This represents the
              CSI dependencies within a SI.              
              Writable only when
              saAmfCsiRowStatus is not active"
         ::= { saAmfCSITableEntry 3 }

     saAmfCSIRowStatus OBJECT-TYPE 
         SYNTAX      RowStatus
         MAX-ACCESS  read-create
         STATUS      current
         DESCRIPTION
             "This variable is used to create,
              modify, and/or delete a row in
              this table. saAmfCSType and saAmfCSIRank
              objects need to be set to valid
              value to make the status active.
              The SaAmfCSINameValueTableEntry s 
              for this CSI should be added
              before this object is set to active.
              It can be set to delete or not-in-service
              only if the saAmfSIAdminState 
              of the SI to which this CSI belongs
              is locked. It can be deleted only
              after all the entries in 
              saAmfCSINameValueTable, with this
              CSI name as primary index is deleted. "
         ::= { saAmfCSITableEntry 4 }


     --****************************************************************
     -- AMF CSI Name-Value Table Objects - the name/value pairs for
     -- CSIs are configured through this table.
     --****************************************************************
          
     saAmfCSINameValueTable OBJECT-TYPE
         SYNTAX      SEQUENCE OF SaAmfCSINameValueTableEntry
         MAX-ACCESS  not-accessible
         STATUS      current
         DESCRIPTION
             "This table is used to configure the name/value
              pairs for CSIs. The name/value pairs for a CSI
              should be configured after the CSI entry is
              created in the saAmfCSITable, but before the
              rowstatus for the entry is made active."
              
         ::= { saAmfTables 12 }

     saAmfCSINameValueTableEntry OBJECT-TYPE
         SYNTAX      SaAmfCSINameValueTableEntry
         MAX-ACCESS  not-accessible
         STATUS      current
         DESCRIPTION
             "An entry in this table represents a name/value
              pair associated with a CSI"
         INDEX       { saAmfCSINameValueCSIName, saAmfCSINameValueParamName }
         ::= { saAmfCSINameValueTable 1 }

     SaAmfCSINameValueTableEntry ::= SEQUENCE {
         saAmfCSINameValueCSIName         SnmpAdminString,
         saAmfCSINameValueParamName       SnmpAdminString,
         saAmfCSINameValueParamValue      SnmpAdminString,
         saAmfCSINameValueRowStatus       RowStatus
     }

     saAmfCSINameValueCSIName OBJECT-TYPE 
         SYNTAX      SnmpAdminString
         MAX-ACCESS  accessible-for-notify
         STATUS      current
         DESCRIPTION
             "The identifier of the CSI to which name/value pair
              is associated"
         ::= { saAmfCSINameValueTableEntry 1 }

     saAmfCSINameValueParamName OBJECT-TYPE 
         SYNTAX      SnmpAdminString
         MAX-ACCESS  accessible-for-notify
         STATUS      current
         DESCRIPTION
             "The name part of the name/value pair"
         ::= { saAmfCSINameValueTableEntry 2 }

     saAmfCSINameValueParamValue OBJECT-TYPE 
         SYNTAX      SnmpAdminString
         MAX-ACCESS  read-create
         STATUS      current
         DESCRIPTION
             "The value string of the parameter. This is optional"
         ::= { saAmfCSINameValueTableEntry 3 }

     saAmfCSINameValueRowStatus OBJECT-TYPE 
         SYNTAX      RowStatus
         MAX-ACCESS  read-create
         STATUS      current
         DESCRIPTION
             "This variable is used to create or delete a row in
              this table. It can be set to delete or not-in-service
              only if saAmfCsiRowStatus is not in service or
              not ready."
         ::= { saAmfCSINameValueTableEntry 4 }

     --****************************************************************
     -- AMF  CS Type Name-paramName - This table designates what are the
     -- various params names that a CSI of a particular type supports.
     --****************************************************************
     saAmfCSTypeParamTable OBJECT-TYPE
         SYNTAX      SEQUENCE OF SaAmfCSTypeParamEntry
         MAX-ACCESS  not-accessible
         STATUS      current
         DESCRIPTION
             "This table designates what are
              the various param names that a
              CSI of a particular type supports"
         ::= { saAmfTables 13 } 

     saAmfCSTypeParamEntry OBJECT-TYPE 
         SYNTAX      SaAmfCSTypeParamEntry
         MAX-ACCESS  not-accessible
         STATUS      current
         DESCRIPTION
             "An entry in this table represents a parameter name
              associated with a CSI of a particular type."
         INDEX {saAmfCSTypeName, saAmfCSTypeParamName}
         ::= { saAmfCSTypeParamTable 1 }

     SaAmfCSTypeParamEntry ::= SEQUENCE {
         saAmfCSTypeName            SnmpAdminString, 
         saAmfCSTypeParamName       SnmpAdminString,
         saAmfCSTypeParamRowStatus  RowStatus
     }

    saAmfCSTypeName OBJECT-TYPE
         SYNTAX      SnmpAdminString
         MAX-ACCESS  accessible-for-notify
         STATUS      current
         DESCRIPTION
             "The name of the  CS Type in question whose parameters
              need to be viewed."
         ::= { saAmfCSTypeParamEntry 1 }

     saAmfCSTypeParamName OBJECT-TYPE
         SYNTAX      SnmpAdminString
         MAX-ACCESS  accessible-for-notify
         STATUS      current
         DESCRIPTION
             "The name of the parameter which belongs to the CS Type
              designated by saAmfCSTypeName."
         ::= { saAmfCSTypeParamEntry 2 }

     saAmfCSTypeParamRowStatus OBJECT-TYPE
         SYNTAX      RowStatus
         MAX-ACCESS  read-create
         STATUS      current
         DESCRIPTION
             "This value can be used to create or delete a row in
              this table. A row can only be added or deleted if there
              are no CSIs that are derived from the CSType of the row"
         ::= { saAmfCSTypeParamEntry 3 }


     --****************************************************************
     -- AMF Service unit Service Instance relationship   Table Objects
     --****************************************************************

          
     saAmfSUSITable OBJECT-TYPE
         SYNTAX      SEQUENCE OF SaAmfSUSITableEntry
         MAX-ACCESS  not-accessible
         STATUS      current
         DESCRIPTION
             "The Service unit - Service Instance relationship
              Table identifies all the SU SI relationships 
              that exists in the cluster. AMF adds entries
              to this table, there is no provision for an
              operator to create entries dynamically. This is
              because the AMF is responsible for determining
              SU assignments for SIs"
              
         ::= { saAmfTables 14 }

     saAmfSUSITableEntry OBJECT-TYPE
         SYNTAX      SaAmfSUSITableEntry
         MAX-ACCESS  not-accessible
         STATUS      current
         DESCRIPTION
             "An entry in this table represents a 
              SU SI relationship in the AMF
              cluster environment. An entry is
              automatically created and
              destroyed by the AMF system when
              a SI is assigned or un assigned
              to a SU."
         INDEX       {  saAmfSUSISuName, saAmfSUSISiName  }
         ::= { saAmfSUSITable 1 }

     SaAmfSUSITableEntry ::= SEQUENCE {
         saAmfSUSISuName                           SnmpAdminString,
         saAmfSUSISiName                           SnmpAdminString,
         saAmfSUSIHAState                          SaAmfHAState,
         saAmfSUSISGName                           SnmpAdminString 
     }

     saAmfSUSISuName OBJECT-TYPE 
         SYNTAX      SnmpAdminString
         MAX-ACCESS  accessible-for-notify
         STATUS      current
         DESCRIPTION
             "A octet string that
              uniquely identifies a
              service unit name that has
              been assigned an SI."
         ::= { saAmfSUSITableEntry 1 }

     saAmfSUSISiName OBJECT-TYPE 
         SYNTAX      SnmpAdminString
         MAX-ACCESS  accessible-for-notify
         STATUS      current
         DESCRIPTION
             "An octet string that
              uniquely identifies a
              service instance"
         ::= { saAmfSUSITableEntry 2 }


     saAmfSUSIHAState OBJECT-TYPE 
         SYNTAX      SaAmfHAState 
         MAX-ACCESS  read-only
         STATUS      current
         DESCRIPTION
             "This value denotes The current
              HA state for the SI assignment to an SU"
         ::= { saAmfSUSITableEntry 3 }

     saAmfSUSISGName OBJECT-TYPE 
         SYNTAX      SnmpAdminString 
         MAX-ACCESS  read-only
         STATUS      current
         DESCRIPTION
             "This value denotes the name of the SG 
              which contains the SU that is assigned the 
              particular SI designated in this table."
         ::= { saAmfSUSITableEntry 4 }



     --****************************************************************
     -- AMF Health Check  Table Objects
     --****************************************************************

          
     saAmfHealthCheckTable OBJECT-TYPE
         SYNTAX      SEQUENCE OF SaAmfHealthCheckTableEntry
         MAX-ACCESS  not-accessible
         STATUS      current
         DESCRIPTION
             "The Health Check Table identifies all
              the health check records that are used
              by components to perform health check.
              "
         ::= { saAmfTables 15 }

     saAmfHealthCheckTableEntry OBJECT-TYPE
         SYNTAX      SaAmfHealthCheckTableEntry
         MAX-ACCESS  not-accessible
         STATUS      current
         DESCRIPTION
             "An entry in this table represents a 
              record that is associated with a set
              of parameters (like periodicity and duration)."
         INDEX       {  saAmfHealthCompName, saAmfHealthCheckKey  }
         ::= { saAmfHealthCheckTable 1 }

     SaAmfHealthCheckTableEntry ::= SEQUENCE {
         saAmfHealthCompName                       SnmpAdminString,
         saAmfHealthCheckKey                       OCTET STRING,
         saAmfHealthCheckPeriod                    SafTimeStamp,
         saAmfHealthCheckMaxDuration               SafTimeStamp,
         saAmfHealthCheckRowStatus                 RowStatus
     }

     saAmfHealthCompName OBJECT-TYPE 
         SYNTAX      SnmpAdminString
         MAX-ACCESS  accessible-for-notify
         STATUS      current
         DESCRIPTION
             "An octet string that
              uniquely identifies a component"
         ::= { saAmfHealthCheckTableEntry 1 }

     saAmfHealthCheckKey OBJECT-TYPE 
         SYNTAX      OCTET STRING(SIZE(1..32))
         MAX-ACCESS  accessible-for-notify
         STATUS      current
         DESCRIPTION
             "An octet string that
              uniquely identifies a
              health check key name."
         ::= { saAmfHealthCheckTableEntry 2 }

     saAmfHealthCheckPeriod OBJECT-TYPE 
         SYNTAX      SafTimeStamp
         MAX-ACCESS  read-create
         STATUS      current
         DESCRIPTION
             "This is the time interval at
              which health check is performed
              by the component. The value is
              in units of nano seconds. The
              minimum value is
              10 milli seconds(10000000)
              writable only saAmfHealthCheckRowStatus
              is not active."
         ::= { saAmfHealthCheckTableEntry 3 }

     saAmfHealthCheckMaxDuration OBJECT-TYPE 
         SYNTAX      SafTimeStamp
         MAX-ACCESS  read-create
         STATUS      current
         DESCRIPTION
             "Time in milliseconds during which the AMF 
              expects the response to a healthcheck.
              The value is in units of
              nano seconds. The minimum
              value is 10 milli seconds(10000000)
              writable only saAmfHealthCheckRowStatus
              is not active."
         ::= { saAmfHealthCheckTableEntry 4 }

     saAmfHealthCheckRowStatus OBJECT-TYPE 
         SYNTAX      RowStatus
         MAX-ACCESS  read-create
         STATUS      current
         DESCRIPTION
             "This variable is used to create,
              modify, and/or delete a row in
              this table."
         ::= { saAmfHealthCheckTableEntry 5 }


     --****************************************************************
     -- AMF Status component component service Instance relationship
     --  Table Objects
     --****************************************************************

          
     saAmfSCompCsiTable OBJECT-TYPE
         SYNTAX      SEQUENCE OF SaAmfSCompCsiTableEntry
         MAX-ACCESS  not-accessible
         STATUS      current
         DESCRIPTION
             "This Status component 
              component service Instance relationship
              Table identifies the status of the 
              component component service Instance
              relationships   
              that currently exists in the cluster."
              
         ::= { saAmfTables 16 }

     saAmfSCompCsiTableEntry OBJECT-TYPE
         SYNTAX      SaAmfSCompCsiTableEntry
         MAX-ACCESS  not-accessible
         STATUS      current
         DESCRIPTION
             "The status component CSI relationship
              entries are created and destroyed as
              and when the system assigns or unassigns
              an SI to an SU of which the CSI and 
              components are a part of."
         INDEX       {  saAmfSCompCsiCompName, saAmfSCompCsiCsiName  }
         ::= { saAmfSCompCsiTable 1 }

     SaAmfSCompCsiTableEntry ::= SEQUENCE {
         saAmfSCompCsiCompName                     SnmpAdminString,
         saAmfSCompCsiCsiName                      SnmpAdminString,
         saAmfSCompCsiHAState                      SaAmfHAState
     }

     saAmfSCompCsiCompName OBJECT-TYPE 
         SYNTAX     SnmpAdminString
         MAX-ACCESS  accessible-for-notify
         STATUS      current
         DESCRIPTION
             "This object is An octet string
              that denotes a component name, which
              has been assigned a CSI."
         ::= { saAmfSCompCsiTableEntry 1 }

     saAmfSCompCsiCsiName OBJECT-TYPE 
         SYNTAX     SnmpAdminString
         MAX-ACCESS  accessible-for-notify
         STATUS      current
         DESCRIPTION
             "This object is An octet string
              that denotes a component service 
              instance name, which has been assigned
              to a component."
         ::= { saAmfSCompCsiTableEntry 2 }

     saAmfSCompCsiHAState OBJECT-TYPE 
         SYNTAX      SaAmfHAState
         MAX-ACCESS  read-only
         STATUS      current
         DESCRIPTION
             "The current HA state for the CSI
              w.r.t Component."
         ::= { saAmfSCompCsiTableEntry 3 }

-- *****************************************************************************
--   Notifications : This section enumerates the Traps that the AMF implementation 
--                   is expected to support.
--   TrapObject  : Object values delivered in one or more traps which 
--                 are not defined in any previous scalar or table in this MIB.
--   Traps       : Actual Traps specified in this MIB
-- ******************************************************************************
saAmfTrapObject  OBJECT IDENTIFIER ::= { safAmfNotifications 1 }
saAmfTraps       OBJECT IDENTIFIER ::= { safAmfNotifications 2 }

saAmfSvcUserName  OBJECT-TYPE
        SYNTAX       SnmpAdminString
        MAX-ACCESS   read-only
        STATUS       current
        DESCRIPTION
           "The LDAP DN of the component which is a client of AMF."
        ::= { saAmfTrapObject 1 }

saAmfErrorCode OBJECT-TYPE
        SYNTAX       SafAISErrorReturnCode
        MAX-ACCESS   read-only
        STATUS       current
        DESCRIPTION
           "A subset of Error code values that are possible
            in the context of AMF. There are two trap cases:
            ClientMisbehaving- a client using a AMF API incorrectly.
            ServiceImpaired - The AMF service is impaired for some reason."
        ::= { saAmfTrapObject 2 }

-- ***************************************************************************
--   AMF Traps 
-- ***************************************************************************
saAmfAlarmServiceImpaired NOTIFICATION-TYPE
        OBJECTS {
                saAmfErrorCode
        }
        STATUS             current
        DESCRIPTION
           "The AMF service is not able to provide its service for one
            of several reasons. The 'saAmfErrorCode' explains why AMF is
            unable to provide service"
        ::= { saAmfTraps 1 }

saAmfAlarmCompInstantiationFailed NOTIFICATION-TYPE
        OBJECTS {
                  saAmfCompName
           }
        STATUS             current
        DESCRIPTION
           "This trap notifies the system administrator that AMF was unable to 
            successfully instantiate the component 'saAmfCompName'. The specific 
            mechanism used to instantiate a component will vary based on component
            category."
       ::= { saAmfTraps 2 }

saAmfAlarmCompTerminationFailed NOTIFICATION-TYPE
        OBJECTS {
                  saAmfCompName
           }
        STATUS             current
        DESCRIPTION
           "This trap notifies the system administrator that AMF was unable to 
            successfully terminate the component 'saAmfCompName'. The specific 
            mechanism used to terminate a component will vary based on component
            category."
       ::= { saAmfTraps 3 }

saAmfAlarmCompCleanupFailed NOTIFICATION-TYPE
        OBJECTS {
                  saAmfCompName
           }
        STATUS             current
        DESCRIPTION
           "This trap notifies the system administrator that AMF was unable to 
            successfully cleanup the component 'saAmfCompName'. The specific 
            mechanism used to cleanup a component will vary based on component
            category."
       ::= { saAmfTraps 4 }

saAmfAlarmClusterReset NOTIFICATION-TYPE
        OBJECTS {
                  saAmfCompName
           }
        STATUS             current
        DESCRIPTION
           "A component designated by 'saAmfCompName' failed and a cluster reset 
		    recovery as recommended by the component is being done."
       ::= { saAmfTraps 5 }

saAmfAlarmSIUnassigned NOTIFICATION-TYPE
        OBJECTS {
                  saAmfSIName
           }
        STATUS             current
        DESCRIPTION
           "A particular work assignment indicated by the 'saAmfSIName' is no longer assigned to a SU
            and is potentially causing a service disruption. This alarm is typically generated when AMF
            was unable to successfully execute recovery policies in case of a failure (Node/SU etc.) inorder
            to prevent the service disruption and maintain service availability."
       ::= { saAmfTraps 6 }

saAmfStateChgNodeAdmin NOTIFICATION-TYPE
        OBJECTS {
                saAmfNodeName,
                saAmfNodeAdminState
         }
        STATUS             current
        DESCRIPTION
           "Triggered when the administrative state of a Node 'saAmfNodeName' 
            changes. This Notification also contains the current administrative state
            of the Node designated by 'saAmfNodeAdminState'."
        ::= { saAmfTraps 7 }

saAmfStateChgSGAdmin NOTIFICATION-TYPE
        OBJECTS {
                saAmfSGName,
                saAmfSGAdminState
        }
        STATUS             current
        DESCRIPTION
           "Triggered when the administrative state of a SG 'saAmfSGName' 
            changes. This Notification also contains the current administrative state
            of the SG designated by 'saAmfSGAdminState'"
        ::= { saAmfTraps 8 }

saAmfStateChgSUAdmin NOTIFICATION-TYPE
        OBJECTS {
                saAmfSUName,
                saAmfSUAdminState
        }
        STATUS             current
        DESCRIPTION
           "Triggered when the administrative state of a SU 'saAmfSUName' 
            changes. This Notification also contains the current administrative state
            of the SU designated by 'saAmfSUAdminState'"
        ::= { saAmfTraps 9 }

saAmfStateChgSIAdmin NOTIFICATION-TYPE
        OBJECTS {
                saAmfSIName,
                saAmfSIAdminState
        }
        STATUS             current
        DESCRIPTION
           "Triggered when the administrative state of a SI 'saAmfSIName' 
            changes. This Notification also contains the current administrative state
            of the SI designated by 'saAmfSIAdminState'"
        ::= { saAmfTraps 10 }


saAmfStateChgSUOper NOTIFICATION-TYPE
        OBJECTS {
                saAmfSUName,
                saAmfSUOperState
        }
        STATUS             current
        DESCRIPTION
           "Triggered when the operational state of a SU 'saAmfSUName' 
            changes.This Notification also contains the current operational state
            of the SU designated by 'saAmfSUOperState'"
        ::= { saAmfTraps 11 }

saAmfStateChgSIOper NOTIFICATION-TYPE
        OBJECTS {
                saAmfSIName,
                saAmfSIOperState
        }
        STATUS             current
        DESCRIPTION
           "Triggered when the operational state of a SI 'saAmfSIName' 
            changes.This Notification also contains the current operational state
            of the SI designated by 'saAmfSIOperState'"
        ::= { saAmfTraps 12 }

saAmfStateChgSUPresence NOTIFICATION-TYPE
        OBJECTS {
                saAmfSUName,
                saAmfSUPresenceState
        }
        STATUS             current
        DESCRIPTION
           "Triggered when the presence state of a SU 'saAmfSUName' 
            changes to Instantiated, Uninstantiated or Restarting.
            This Notification also contains the current presence state
            of the SU designated by 'saAmfSUPresenceState'."
        ::= { saAmfTraps 13 }

saAmfStateChgSUHaState NOTIFICATION-TYPE
        OBJECTS {
                saAmfSUSISuName , 
                saAmfSUSISiName , 
                saAmfSUSIHAState 
        }
        STATUS             current
        DESCRIPTION
           "Produced when the HA state of a SU 'saAmfSUSISuName' 
            changes for a particular SI 'saAmfSUSISiName' assigned to the SU.
            This Notification also contains the current HA state
            of the SU designated by 'saAmfSUSIHAState' for the SI in question.
            This notification should also be produced when a SI is assigned 
            to a service unit for the very first time"
        ::= { saAmfTraps 14 }

saAmfStateChgProxiedCompOrphaned NOTIFICATION-TYPE
        OBJECTS {
                 saAmfCompCurrProxyName, 
                 saAmfCompName   
        }
        STATUS             current
        DESCRIPTION
           "The proxy component 'saAmfCompCurrProxyName' overseeing 
            a proxied 'saAmfCompName' failed. So the proxied component
            is currently un-supervised. One such notification must be 
            generated for every proxied component which was being 
            supervised by the failed proxy."
        ::= { saAmfTraps 15 }

-- ***************************************************************************
--    OBJECT GROUPS Declarations for SMIv2 
-- ***************************************************************************
 saMIBCompliances OBJECT IDENTIFIER  ::= { saAmfCompliances 1 }
 saAmfGroup OBJECT-GROUP
         OBJECTS {
     saAmfAgentSpecVersion,
     saAmfAgentVendor,
     saAmfAgentVendorProductRev,
     saAmfServiceStartEnabled,
     saAmfServiceState,
     saAmfClusterStartupTimeout,
     saAmfNodeName , 
     saAmfNodeSuFailoverProb , 
     saAmfNodeSuFailoverMax , 
     saAmfNodeAdminState,
     saAmfNodeRowStatus , 
     saAmfSGName,
     saAmfSGRedModel,   
     saAmfSGFailbackOption,  
     saAmfSGNumPrefActiveSUs,
     saAmfSGNumPrefStandbySUs,
     saAmfSGNumPrefInserviceSUs,
     saAmfSGNumPrefAssignedSUs,
     saAmfSGMaxActiveSIsperSU,
     saAmfSGMaxStandbySIsperSU,
     saAmfSGAdminState,
     saAmfSGCompRestartProb,
     saAmfSGCompRestartMax,
     saAmfSGSuRestartProb,
     saAmfSGSuRestartMax,
     saAmfSGNumCurrAssignedSU,   
     saAmfSGNumCurrNonInstantiatedSpareSU,  
     saAmfSGNumCurrSpareSU, 
     saAmfSGRowStatus,
     saAmfSUName,
     saAmfSURank,  
     saAmfSUNumComponents, 
     saAmfSUNumCurrActiveSIs,
     saAmfSUNumCurrStandbySIs,
     saAmfSUAdminState,
     saAmfSUFailOver,
     saAmfSUReadinessState,
     saAmfSUOperState,
     saAmfSUPresenceState,
     saAmfSUPreInstantiable,
     saAmfSUParentSGName,
     saAmfSUIsExternal,
     saAmfSURowStatus,
     saAmfSIName,
     saAmfSIRank,
     saAmfSINumCSIs,                                                 
     saAmfSIPrefNumAssignments,
     saAmfSIAdminState,
     saAmfSIOperState, 
     saAmfSINumCurrActiveAssignments,
     saAmfSINumCurrStandbyAssignments,
     saAmfSIParentSGName,
     saAmfSIRowStatus,
     saAmfSUsperSIName,
     saAmfSUsperSIRank,
     saAmfSUsperSISUName,
     saAmfSUsperSIRowStatus, 
     saAmfSGSIRankSGName,
     saAmfSGSIRank,
     saAmfSGSIRankSIName,
     saAmfSGSURankSGName,
     saAmfSGSURank,
     saAmfSGSURankSUName,
     saAmfSISIDepSIName,
     saAmfSISIDepDepndSIName,
     saAmfSISIDepToltime,
     saAmfSISIDepRowStatus,
     saAmfCompName,
     saAmfCompCapability,
     saAmfCompCategory,
     saAmfCompInstantiateCmd,
     saAmfCompTerminateCmd,
     saAmfCompCleanupCmd,
     saAmfCompAmStartCmd,
     saAmfCompAmStopCmd,
     saAmfCompAmStartTimeout,
     saAmfCompAmStopTimeout,
     saAmfCompInstantiationLevel,
     saAmfCompInstantiateTimeout,
     saAmfCompDelayBetweenInstantiateAttempts,
     saAmfCompTerminateTimeout,
     saAmfCompCleanupTimeout,
     saAmfCompTerminateCallbackTimeOut,
     saAmfCompCSISetCallbackTimeout,
     saAmfCompQuiescingCompleteTimeout,
     saAmfCompCSIRmvCallbackTimeout,
     saAmfCompProxiedCompInstantiateCallbackTimeout,
     saAmfCompProxiedCompCleanupCallbackTimeout,
     saAmfCompNodeRebootCleanupFail,
     saAmfCompRecoveryOnError,
     saAmfCompNumMaxInstantiate,
     saAmfCompNumMaxInstantiateWithDelay,
     saAmfCompNumMaxAmStartAttempts,     
     saAmfCompNumMaxAmStopAttempts,
     saAmfCompDisableRestart,
     saAmfCompNumMaxActiveCsi,
     saAmfCompNumMaxStandbyCsi,    
     saAmfCompNumCurrActiveCsi,
     saAmfCompNumCurrStandbyCsi,
     saAmfCompRestartCount,
     saAmfCompOperState,
     saAmfCompPresenceState,
     saAmfCompReadinessState,
     saAmfCompCurrProxyName,
     saAmfCompRowStatus,
     saAmfCompCSTypeSupportedCompName,
     saAmfCompCSTypeSupportedCSIName,
     saAmfCompCSTypeSupportedRowStatus,
     saAmfCSIName , 
     saAmfCSType , 
     saAmfCSIRank , 
     saAmfCSIRowStatus , 
     saAmfCSINameValueCSIName , 
     saAmfCSINameValueParamName , 
     saAmfCSINameValueParamValue , 
     saAmfCSINameValueRowStatus ,
     saAmfCSTypeName,
     saAmfCSTypeParamName,
     saAmfCSTypeParamRowStatus, 
     saAmfSUSISuName , 
     saAmfSUSISiName , 
     saAmfSUSIHAState ,
     saAmfSUSISGName,
     saAmfHealthCompName, 
     saAmfHealthCheckKey , 
     saAmfHealthCheckPeriod , 
     saAmfHealthCheckMaxDuration , 
     saAmfHealthCheckRowStatus , 
     saAmfSCompCsiCompName , 
     saAmfSCompCsiCsiName , 
     saAmfSCompCsiHAState,
     saAmfSvcUserName,
     saAmfErrorCode 
                 }
        STATUS current
        DESCRIPTION
                "AMF Compliance Group."
        ::= { saMIBCompliances 1 }

saAmfNotificationsGroup  NOTIFICATION-GROUP
    NOTIFICATIONS { 
                  saAmfAlarmCompInstantiationFailed,
                  saAmfAlarmCompTerminationFailed,
				  saAmfAlarmCompCleanupFailed,	
                  saAmfAlarmClusterReset,
				  saAmfAlarmSIUnassigned,
                  saAmfAlarmServiceImpaired,
                  saAmfStateChgNodeAdmin,
                  saAmfStateChgSGAdmin,
                  saAmfStateChgSUAdmin,
                  saAmfStateChgSIAdmin,
                  saAmfStateChgSUOper,
                  saAmfStateChgSIOper,
                  saAmfStateChgSUPresence,
                  saAmfStateChgSUHaState,
                  saAmfStateChgProxiedCompOrphaned
          }
    STATUS  current
    DESCRIPTION
            "The set of Notifications that must be supported by an Amf
             implementation."
    ::= { saMIBCompliances 2}

-- ***************************************************************************
--  MODULE COMPLIANCE Declarations for SMIv2 
-- ***************************************************************************
saAmfMIBCompliance MODULE-COMPLIANCE
         STATUS current
         DESCRIPTION
          "The compliance statement for SMIv2 compliance of AMF MIB."
         MODULE 
         MANDATORY-GROUPS { saAmfGroup,
                            saAmfNotificationsGroup
          }
         ::= { saMIBCompliances 3 }

END
