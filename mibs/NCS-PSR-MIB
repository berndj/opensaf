NCS-PSR-MIB DEFINITIONS ::= BEGIN


IMPORTS
     MODULE-IDENTITY, OBJECT-TYPE
                  FROM SNMPv2-SMI
     RowStatus
                  FROM SNMPv2-TC

     MODULE-COMPLIANCE, OBJECT-GROUP
  	          FROM SNMPv2-CONF

     openSafModules, pssv 
                  FROM OPENSAF-SMI;
     

     ncsPSSv MODULE-IDENTITY
        LAST-UPDATED "200509230000Z" -- Sept 23, 2005 
        ORGANIZATION "OpenSAF Foundation"
        CONTACT-INFO
        "www.opensaf.org"
        DESCRIPTION
	     "This Enterprise MIB contains managed object definitions for the
              Persistent Store Restore Service of Netplane Core
              Services.

              (C) Copyright 2008 The OpenSAF Foundation

              This program is distributed in the hope that it will be useful, but
              WITHOUT ANY WARRANTY; without even the implied warranty of MERCHANTABILITY
              or FITNESS FOR A PARTICULAR PURPOSE. This file and program are licensed
              under the GNU Lesser General Public License Version 2.1, February 1999.
              The complete license can be accessed from the following location:
              http://opensource.org/licenses/lgpl-license.php
              See the Copying file included with the OpenSAF distribution for full
              licensing terms.

              Author(s): Emerson Network Power"


	    REVISION "200306010000Z"
		DESCRIPTION
		"This Mib describes configuration of various PSSv
		commands through MIB"
     ::= { openSafModules 7}

--****************************************************************

ncspssvObjects                  OBJECT IDENTIFIER ::= { pssv 1 }

ncsPSSvScalars                  OBJECT IDENTIFIER ::= { ncspssvObjects 1 }
ncsPSSvTables                   OBJECT IDENTIFIER ::= { ncspssvObjects 2 }


--****************************************************************
-- PSSv Global Objects
--****************************************************************

ncsPSSvExistingProfile OBJECT-TYPE
    SYNTAX       OCTET STRING (SIZE(0..256))
    MAX-ACCESS   read-write
    STATUS       current
    DESCRIPTION
       "1. For performing a LOAD operation, set this scalar to the
           alternate profile to load.
        2. For performing COPY or RENAME operations, set this scalar to 
           the profile to copy/rename.
        3. For performing a REPLACE operation on current profile, 
           set this scalar to the name of the alternate profile 
           that replaces the current profile.
        In case this object is not set, any GET on this object would
        return a NULL string.
        However, a SET on this object for NULL string is not allowed."
        ::= { ncsPSSvScalars 1 }


ncsPSSvNewProfile OBJECT-TYPE
    SYNTAX       OCTET STRING (SIZE(0..256))
    MAX-ACCESS   read-write
    STATUS       current
    DESCRIPTION
       "1. For performing a COPY operation, set this scalar to the
           new profile to create.
        2. For performing a RENAME operation, set this scalar to 
           the new name for the existing profile.
        In case this object is not set, any GET on this object would 
        return a NULL string.
        However, a SET on this object for NULL string is not allowed."
        ::= { ncsPSSvScalars 2 }


ncsPSSvTriggerOperation OBJECT-TYPE
    SYNTAX       INTEGER { noop(0), load(1), save(2), 
                           copy(3), rename(4), replace(5),
                           reloadlibconf(6), reloadspcnlist(7) }
    MAX-ACCESS   read-write
    STATUS       current
    DESCRIPTION
       "Setting this scalar triggers the corresponding operation. The
        PSSv sets this object to no_op on completion of the operation.
        Note that saving the current configuration can be done by 
        triggering a SAVE operation.
        1. Load operation performs the on-demand playback from an
           alternate configuration profile onto the current profile.
        2. In order to save the current configuration to a named profile,
           create a new row in the PSSv Profile Table.
        3. Copy operation creates a copy of a particular configuration profile.
        4. Rename operation changes the name of a particular configuration 
           profile.
        5. Replace operation removes current profile and replaces with
           the alternate profile.
        6. reloadlibconf operation reloads the application MIB definitions
           into PSSv from the static configuration file (pssv_lib.conf).
        7. reloadspcnlist reloads the system-clients(SPCN) details into 
           PSSv from the static configuration file (pssv_spcn.list)."
        ::= { ncsPSSvScalars 3 }

ncsPSSvCurrentProfile OBJECT-TYPE
    SYNTAX       OCTET STRING (SIZE(1..256))
    MAX-ACCESS   read-write
    STATUS       current
    DESCRIPTION
       "Name of the current configuration profile."
        ::= { ncsPSSvScalars 4 }



--****************************************************************
-- PSSv Command Table Objects
--****************************************************************

ncsPSSvProfileTable OBJECT-TYPE
    SYNTAX   SEQUENCE OF NCSPSSvProfileTableEntry
    MAX-ACCESS not-accessible
    STATUS   current
    DESCRIPTION
       "PSSv Command Table"
    REFERENCE
       "No Reference"
    ::= { ncsPSSvTables 1 }

ncsPSSvProfileTableEntry OBJECT-TYPE
    SYNTAX   NCSPSSvProfileTableEntry
    MAX-ACCESS not-accessible
    STATUS   current
    DESCRIPTION
       "A row in the PSSv Profile Table"
    INDEX { ncsPSSvProfileName }
    ::= { ncsPSSvProfileTable 1 }

NCSPSSvProfileTableEntry ::=
    SEQUENCE {
 	ncsPSSvProfileName
	    OCTET STRING,
   	ncsPSSvProfileDesc
	    OCTET STRING,
   	ncsPSSvProfileTableStatus
            RowStatus
    }

ncsPSSvProfileName OBJECT-TYPE
    SYNTAX   OCTET STRING (SIZE(1..256))
    MAX-ACCESS not-accessible
    STATUS   current
    DESCRIPTION
       "The name of the configuration profile. Can be 256 characters long"
    ::= { ncsPSSvProfileTableEntry 1 }


ncsPSSvProfileDesc OBJECT-TYPE
    SYNTAX   OCTET STRING (SIZE(0..256))
    MAX-ACCESS read-create
    STATUS   current
    DESCRIPTION
       "Description of the configuration profile. Can be up to 256
        characters long. If this object is not set, it will be treated as
        as NULL string.
        However, a SET on this object for NULL string is not allowed."
    ::= { ncsPSSvProfileTableEntry 2 }


ncsPSSvProfileTableStatus OBJECT-TYPE
    SYNTAX RowStatus  
    MAX-ACCESS read-create
    STATUS   current
    DESCRIPTION
     	  "The row status variable, used according to
           row installation and removal conventions. A row is created when
	   one wants to save the current configuration."
    ::= { ncsPSSvProfileTableEntry 3 }


-- conformance and group information
ncsPSSvConformance OBJECT IDENTIFIER ::= { ncsPSSv 3 }
ncsPSSvGroups      OBJECT IDENTIFIER ::= { ncsPSSvConformance 1 }
ncsPSSvCompliances OBJECT IDENTIFIER ::= { ncsPSSvConformance 2 }

-- compliance statements

ncsPSSvCompliance MODULE-COMPLIANCE
   STATUS  current
   DESCRIPTION
       "The compliance statement for SNMPv2 entities
       which implement the ncsPSSv MIB."

   MODULE  -- this module
   MANDATORY-GROUPS { ncsPSSvGroup }

   ::= { ncsPSSvCompliances 1 }

-- units of conformance

ncsPSSvGroup OBJECT-GROUP
    OBJECTS { ncsPSSvExistingProfile, ncsPSSvNewProfile, ncsPSSvTriggerOperation,
	      ncsPSSvProfileDesc, ncsPSSvProfileTableStatus
	}
    STATUS  current
    DESCRIPTION
       "The PSSv Table."
    ::= { ncsPSSvGroups 1 }

END
