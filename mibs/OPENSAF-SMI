OPENSAF-SMI DEFINITIONS ::= BEGIN
    IMPORTS
    	enterprises, MODULE-IDENTITY
    FROM SNMPv2-SMI;

-- Contact Info
-- OpenSAF Foundation
-- www.opensaf.org
 
-- REVISION HISTORY
-- 27th Jan 2005
-- Initial Version with numbers allotted for NCS.

-- 29th April 2009
-- Migrated to Private Enterprise Number allotted for OpenSAF project.

-- (C) Copyright 2008 The OpenSAF Foundation
--
-- This program is distributed in the hope that it will be useful, but
-- WITHOUT ANY WARRANTY; without even the implied warranty of MERCHANTABILITY
-- or FITNESS FOR A PARTICULAR PURPOSE. This file and program are licensed
-- under the GNU Lesser General Public License Version 2.1, February 1999.
-- The complete license can be accessed from the following location:
-- http://opensource.org/licenses/lgpl-license.php
-- See the Copying file included with the OpenSAF distribution for full
-- licensing terms.
--
-- Author(s): Emerson Network Power

-- Root of the OpenSAF project enterprise MIB tree
openSaf         OBJECT IDENTIFIER ::= { enterprises 32993 }

-- Subtree for common object and event definitions
openSafObjects  OBJECT IDENTIFIER ::= { openSaf 1 }

-- Sub-tree for specific object and event definitions
openSafProducts    OBJECT IDENTIFIER ::= { openSaf 2 }

-- Sub-tree for experimental definitions
openSafExp    	OBJECT IDENTIFIER ::= { openSaf 3 }

-- Sub-tree for registrations. These object identifiers may be 
-- returned as the values of SNMP queries
openSafReg    	OBJECT IDENTIFIER ::= { openSaf 4 }

-- Sub-tree for agent profiles
openSafCaps 	OBJECT IDENTIFIER ::= { openSaf 5 }

-- Subtree for experimental generic definitions
openSafGenExp      OBJECT IDENTIFIER ::= { openSafExp 1 }

-- Subtree for experimental, product specific objects and events
openSafProductsExp OBJECT IDENTIFIER ::= { openSafExp 2 }

-- Identities assigned to different modules created Under OpenSAF project
openSafModules OBJECT IDENTIFIER ::= { openSafReg 1 }
--opensafAuxModule OBJECT IDENTIFIER ::= { openSafReg 2 }

-- NetPlane Core Services
services OBJECT IDENTIFIER ::= { openSafObjects 1}

-- Availability Service
avsv 	OBJECT IDENTIFIER ::= { services 1 }

-- Interface Service
ifsv 	OBJECT IDENTIFIER ::= { services 2 }

-- Checkpoint Service
cpsv 	OBJECT IDENTIFIER ::= { services 3 }

-- Event Distribution Service
edsv 	OBJECT IDENTIFIER ::= { services 4 }

-- System Resource Monitoring
srmsv 	OBJECT IDENTIFIER ::= { services 5 }

-- Distributed Tracing Service
dtsv 	OBJECT IDENTIFIER ::= { services 6 }

-- Persistence Store and Restore service
pssv 	OBJECT IDENTIFIER ::= { services 7 }

-- Management Access Service
masv 	OBJECT IDENTIFIER ::= { services 8 }

-- NCS SNMP SubAgent
ncsSa 	OBJECT IDENTIFIER ::= { services 9 }

-- Availability Manager
avm 	OBJECT IDENTIFIER ::= { services 10 }

-- Generic for NCS 
generic OBJECT IDENTIFIER ::= { services 11 }

-- ncs Virtula Interface service
ncsVip 	OBJECT IDENTIFIER ::= { services 12 }

-- OpenSAF Fault Management service
nfm 	OBJECT IDENTIFIER ::= { services 13 }

-- Simple Software Upgrate Service
ssu  	OBJECT IDENTIFIER ::= { services 14 }

END
