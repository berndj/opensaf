SAF-AIS-TC-MIB DEFINITIONS ::= BEGIN

IMPORTS
      
        TEXTUAL-CONVENTION
                                  FROM SNMPv2-TC
        MODULE-IDENTITY
                                  FROM SNMPv2-SMI
 
        SafTimeStamp,
        aisE
                                  FROM SAF-TC-MIB
        ;

safAISTCMIB MODULE-IDENTITY

         LAST-UPDATED "0412061200Z"
         ORGANIZATION "Service Availability Forum "
         CONTACT-INFO  "

         Service Availability Forum 
	      Systems Management Working Group

	      5440 SW Westgate Drive, Suite 217
	      Portland, OR 97221
	      Phone: (503) 291-2576
	      Fax: (503) 297-1090

         e-mail: snmp@saforum.org
         "
             
          DESCRIPTION " 
         Definition of Textual Conventions spacifically for 
         the Application Interface Services (AIS) portion of the 
         Service Availability Forum (TM)
         specified SNMP MIBS Copyright(c) 2004 

         See the safTCMIB MODULE-IDENTITY for SAF Namespace taxonomy
         and common textual conventions shared by both HPI and AIS,

         Service Availability Forum (TM)  
         All Rights reserved
         VERSION 1.1 Dec 6, 2004

         These textual conventions are subject to modification by
         the Service Availability Forum (TM) as related SAF
         specifications require.
                "
          ::= { aisE 10}


-- *********************************************************
-- SAF AIS DEFINED TEXTUAL CONVENTIONS
-- *********************************************************
SafAISErrorReturnCode ::= TEXTUAL-CONVENTION
         STATUS current        
         DESCRIPTION " This is an enumeration of the various Error return codes 
         that can be returned by the SAF libraries."
         REFERENCE "SAI-AIS-Overview-B.01.01, Sect. 3.3.13 Error codes"
         SYNTAX INTEGER {  aisok(1),
                           errorlibrary(2),
                           errorversion(3),
                           errorinit(4),
                           errortimeout(5),
                           errortryagain(6),
                           errorinvalidparam(7),
                           errornomemory(8),
                           errorbadhandle(9),
                           errorbusy(10),
                           erroraccess(11),
                           errornotexist(12),
                           errornametoolong(13),
                           errorexist(14),
                           errornospace(15),
                           errorinterrupt(16),
                           errornamenotfound(17),
                           errornoresources(18),
                           errornotsupported(19),
                           errorbadoperation(20),
                           errorfailedoperation(21),
                           errormessageerror(22),
                           errorqueuefull(23),
                           errorqueuenotavailable(24),
                           errorbadflags(25),
                           errortoobig(26),
                           errornosections(27) 
                           }

SafUnsigned64 ::= TEXTUAL-CONVENTION
         STATUS current        
	 DESCRIPTION "The SafUnsigned64 type represents a non-negative
                integer, which may increase or decrease, but shall never
                exceed a maximum value, nor fall below a minimum value. The
                maximum value can not be greater than 2^64-1
                (18446744073709551615 decimal), and the minimum value can
                not be smaller than 0.  The value of a SafUnsigned64
                has its maximum value whenever the information being modeled
                is greater than or equal to its maximum value, and has its
                minimum value whenever the information being modeled is
                smaller than or equal to its minimum value.  If the
                information being modeled subsequently decreases below
                (increases above) the maximum (minimum) value, the
                SafUnsigned64 also decreases (increases).
                
                This textual convention represents a limited and short-term
                solution, and may be deprecated as a long term solution is
                defined and deployed to replace it."

         REFERENCE " Understanding SNMP MIBS, Perkins and McGinnis, pg 51."
	 SYNTAX Opaque (SIZE(4..12))
--      SYNTAX IMPLICIT INTEGER (0..18446744073709551615)
-- *********************************************************
--  END : SAF AIS DEFINED TEXTUAL CONVENTIONS
-- *********************************************************
END
